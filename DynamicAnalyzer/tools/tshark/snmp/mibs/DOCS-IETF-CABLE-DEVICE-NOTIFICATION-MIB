DOCS-IETF-CABLE-DEVICE-NOTIFICATION-MIB DEFINITIONS ::= BEGIN

  IMPORTS
        MODULE-IDENTITY,
        OBJECT-TYPE,
        NOTIFICATION-TYPE,
        mib-2
              FROM SNMPv2-SMI -- RFC 2578
        MODULE-COMPLIANCE,



        OBJECT-GROUP,
        NOTIFICATION-GROUP
              FROM SNMPv2-CONF -- RFC 2580

        docsDevEvLevel,
        docsDevEvId,
        docsDevEvText,
        docsDevSwFilename,
        docsDevSwServer,
        docsDevServerDhcp,
        docsDevServerTime
              FROM DOCS-CABLE-DEVICE-MIB -- RFC 2669

        docsIfCmCmtsAddress,
        docsIfCmtsCmStatusMacAddress,
        docsIfDocsisBaseCapability,
        docsIfCmStatusDocsisOperMode,
        docsIfCmStatusModulationType,
        docsIfCmtsCmStatusDocsisRegMode,
        docsIfCmtsCmStatusModulationType
              FROM DOCS-IF-MIB -- RFC 4546

        ifPhysAddress
              FROM IF-MIB;  -- RFC 2863

  docsDevNotifMIB MODULE-IDENTITY

        LAST-UPDATED    "200605240000Z" -- May 24, 2006
        ORGANIZATION    "IETF IP over Cable Data Network
                         Working Group"

        CONTACT-INFO
            "        Azlina Ahmad
             Postal: Cisco Systems, Inc.
                     170 West Tasman Drive
                     San Jose, CA 95134, U.S.A.
             Phone:   408 853 7927
             E-mail: azlina@cisco.com

                     Greg Nakanishi
             Postal: Motorola
                     6450 Sequence Drive
                     San Diego, CA 92121, U.S.A.
             Phone:   858 404 2366
             E-mail: gnakanishi@motorola.com

             IETF IPCDN Working Group
             General Discussion: ipcdn@ietf.org



             Subscribe: http://www.ietf.org/mailman/listinfo/ipcdn
             Archive: ftp://ftp.ietf.org/ietf-mail-archive/ipcdn
             Co-chairs: Richard Woundy,
                          richard_woundy@cable.comcast.com
                        Jean-Francois Mule, jf.mule@cablelabs.com"

        DESCRIPTION
            "The Event Notification MIB is an extension of the
            CABLE DEVICE MIB.  It defines various notification
            objects for both cable modem and cable modem termination
            systems.  Two groups of SNMP notification objects are
            defined.  One group is for notifying cable modem events,
            and one group is for notifying cable modem termination
            system events.

            DOCSIS defines numerous events, and each event is
            assigned to a functional category.  This MIB defines
            a notification object for each functional category.
            The varbinding list of each notification includes
            information about the event that occurred on the
            device.

            Copyright (C) The Internet Society (2006).  This version
            of this MIB module is part of RFC 4547; see the RFC
            itself for full legal notices."

        REVISION "200605240000Z" -- May 24, 2006
        DESCRIPTION
            "Initial version, published as RFC 4547."
        ::= { mib-2 132 }

docsDevNotifControl OBJECT IDENTIFIER ::= { docsDevNotifMIB 1}
docsDevCmNotifs OBJECT IDENTIFIER ::= { docsDevNotifMIB 2 0 }
docsDevCmtsNotifs OBJECT IDENTIFIER ::= { docsDevNotifMIB 3 0 }

docsDevCmNotifControl OBJECT-TYPE
    SYNTAX BITS {
        cmInitTLVUnknownNotif( 0),
        cmDynServReqFailNotif( 1),
        cmDynServRspFailNotif( 2),
        cmDynServAckFailNotif( 3),
        cmBpiInitNotif( 4),
        cmBPKMNotif( 5),
        cmDynamicSANotif( 6),
        cmDHCPFailNotif( 7),
        cmSwUpgradeInitNotif( 8),
        cmSwUpgradeFailNotif( 9),
        cmSwUpgradeSuccessNotif( 10),



        cmSwUpgradeCVCNotif( 11),
        cmTODFailNotif( 12),
        cmDCCReqFailNotif( 13),
        cmDCCRspFailNotif( 14),
        cmDCCAckFailNotif( 15)
    }
   MAX-ACCESS read-write

   STATUS current
   DESCRIPTION
       "The object is used to enable specific CM notifications.
        For example, if the first bit is set, then
        docsDevCmInitTLVUnknownNotif is enabled.  If it is not set,
        the notification is disabled.  Note that notifications are
        also under the control of the MIB modules defined in
        RFC3413.

        If the device is rebooted,the value of this object SHOULD
        revert to the default value.
       "
   DEFVAL { {} }
   ::= { docsDevNotifControl 1 }

docsDevCmtsNotifControl OBJECT-TYPE
    SYNTAX BITS {
        cmtsInitRegReqFailNotif( 0),
        cmtsInitRegRspFailNotif( 1),
        cmtsInitRegAckFailNotif( 2),
        cmtsDynServReqFailNotif( 3),
        cmtsDynServRspFailNotif( 4),
        cmtsDynServAckFailNotif( 5),
        cmtsBpiInitNotif( 6),
        cmtsBPKMNotif( 7),
        cmtsDynamicSANotif( 8),
        cmtsDCCReqFailNotif( 9),
        cmtsDCCRspFailNotif( 10),
        cmtsDCCAckFailNotif( 11)
    }
    MAX-ACCESS read-write
    STATUS current
    DESCRIPTION
       "The object is used to enable specific CMTS notifications.
        For example, if the first bit is set, then
        docsDevCmtsInitRegRspFailNotif is enabled.  If it is not set,
        the notification is disabled.  Note that notifications are
        also under the control of the MIB modules defined in
        RFC3413.




        If the device is rebooted,the value of this object SHOULD
        revert to the default value.
       "
    DEFVAL { {} }
    ::= { docsDevNotifControl 2 }

docsDevCmInitTLVUnknownNotif NOTIFICATION-TYPE
    OBJECTS {
        docsDevEvLevel,
        docsDevEvId,
        docsDevEvText,
        ifPhysAddress,
        docsIfCmCmtsAddress,
        docsIfDocsisBaseCapability,
        docsIfCmStatusDocsisOperMode,
        docsIfCmStatusModulationType
    }
    STATUS current
    DESCRIPTION
        "Notification to indicate that an unknown TLV was
          encountered during the TLV parsing process.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 1 }





docsDevCmDynServReqFailNotif NOTIFICATION-TYPE
    OBJECTS {
        docsDevEvLevel,
        docsDevEvId,
        docsDevEvText,
        ifPhysAddress,
        docsIfCmCmtsAddress,
        docsIfDocsisBaseCapability,
        docsIfCmStatusDocsisOperMode,
        docsIfCmStatusModulationType
    }
    STATUS current
    DESCRIPTION

        "A notification to report the failure of a dynamic service
         request during the dynamic services process.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected to (if there is a cable
           card/interface in the CMTS, then it is actually the
           MAC address of the cable interface to which it is
           connected).
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 2 }

docsDevCmDynServRspFailNotif NOTIFICATION-TYPE
    OBJECTS {
        docsDevEvLevel,
        docsDevEvId,
        docsDevEvText,
        ifPhysAddress,



        docsIfCmCmtsAddress,
        docsIfDocsisBaseCapability,
        docsIfCmStatusDocsisOperMode,
        docsIfCmStatusModulationType
    }
    STATUS current
    DESCRIPTION
        " A notification to report the failure of a dynamic service
         response during the dynamic services process.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 3}

docsDevCmDynServAckFailNotif NOTIFICATION-TYPE
    OBJECTS {
        docsDevEvLevel,
        docsDevEvId,
        docsDevEvText,
        ifPhysAddress,
        docsIfCmCmtsAddress,
        docsIfDocsisBaseCapability,
        docsIfCmStatusDocsisOperMode,
        docsIfCmStatusModulationType
    }
    STATUS current
    DESCRIPTION



        "A notification to report the failure of a dynamic service
         acknowledgement during the dynamic services process.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 4}

docsDevCmBpiInitNotif NOTIFICATION-TYPE
    OBJECTS {
        docsDevEvLevel,
        docsDevEvId,
        docsDevEvText,
        ifPhysAddress,
        docsIfCmCmtsAddress,
        docsIfDocsisBaseCapability,
        docsIfCmStatusDocsisOperMode,
        docsIfCmStatusModulationType
    }
    STATUS current
    DESCRIPTION
        "A notification to report the failure of a BPI
         initialization attempt during the registration process.

         This notification sends additional information about
         the event by including the following objects in its
         varbinding list.
         - docsDevEvLevel: the priority level associated with the



           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 5 }

docsDevCmBPKMNotif NOTIFICATION-TYPE
    OBJECTS {
        docsDevEvLevel,
        docsDevEvId,
        docsDevEvText,
        ifPhysAddress,
        docsIfCmCmtsAddress,
        docsIfDocsisBaseCapability,
        docsIfCmStatusDocsisOperMode,
        docsIfCmStatusModulationType
    }
    STATUS current
    DESCRIPTION
        "A notification to report the failure of a Baseline
         Privacy Key Management (BPKM) operation.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS



           to which the CM is connected (if there is a cable
           card/interface in the CMTS, then it is actually the
           MAC address of the cable interface to which it is
           connected).
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 6 }

docsDevCmDynamicSANotif NOTIFICATION-TYPE
    OBJECTS {
        docsDevEvLevel,
        docsDevEvId,
        docsDevEvText,
        ifPhysAddress,
        docsIfCmCmtsAddress,
        docsIfDocsisBaseCapability,
        docsIfCmStatusDocsisOperMode,
        docsIfCmStatusModulationType
    }
    STATUS current
    DESCRIPTION
        "A notification to report the failure of a dynamic security
         association operation.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsIfDocsisBaseCapability: the highest
           version of the DOCSIS specification (1.0, 1.1, 2.0)
           that the device is capable of supporting.



         - docsIfCmStatusDocsisOperMode: the QOS level (1.0, 1.1)
           that the CM is operating in.
         - docsIfCmStatusModulationType: the upstream modulation
           methodology used by the CM.
        "
    ::= { docsDevCmNotifs 7 }

docsDevCmDHCPFailNotif NOTIFICATION-TYPE
    OBJECTS {
        docsDevEvLevel,
        docsDevEvId,
        docsDevEvText,
        ifPhysAddress,
        docsIfCmCmtsAddress,
        docsDevServerDhcp,
        docsIfDocsisBaseCapability,
        docsIfCmStatusDocsisOperMode,
        docsIfCmStatusModulationType
    }
    STATUS current
    DESCRIPTION
        "A notification to report the failure of a DHCP operation.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsDevServerDhcp: the IP address of the DHCP server.
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 8 }



docsDevCmSwUpgradeInitNotif NOTIFICATION-TYPE
    OBJECTS {
        docsDevEvLevel,
        docsDevEvId,
        docsDevEvText,
        ifPhysAddress,
        docsIfCmCmtsAddress,
        docsDevSwFilename,
        docsDevSwServer,
        docsIfDocsisBaseCapability,
        docsIfCmStatusDocsisOperMode,
        docsIfCmStatusModulationType
    }
    STATUS current
    DESCRIPTION
        "A notification to indicate that a software upgrade
         has been initiated on the device.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 9 }

docsDevCmSwUpgradeFailNotif NOTIFICATION-TYPE
    OBJECTS {
        docsDevEvLevel,
        docsDevEvId,
        docsDevEvText,



        ifPhysAddress,
        docsIfCmCmtsAddress,
        docsDevSwFilename,
        docsDevSwServer,
        docsIfDocsisBaseCapability,
        docsIfCmStatusDocsisOperMode,
        docsIfCmStatusModulationType
    }
    STATUS current
    DESCRIPTION
        "A notification to report the failure of a software upgrade
         attempt.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsDevSwFilename: the software image file name
         - docsDevSwServer: the IP address of the server that
           the image is retrieved from.
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 10 }

docsDevCmSwUpgradeSuccessNotif NOTIFICATION-TYPE
    OBJECTS {
        docsDevEvLevel,
        docsDevEvId,
        docsDevEvText,
        ifPhysAddress,
        docsIfCmCmtsAddress,



        docsDevSwFilename,
        docsDevSwServer,
        docsIfDocsisBaseCapability,
        docsIfCmStatusDocsisOperMode,
        docsIfCmStatusModulationType
    }
    STATUS current
    DESCRIPTION
        "A notification to report the software upgrade success
         status.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsDevSwFilename: the software image file name
         - docsDevSwServer: the IP address of the server that
           the image is retrieved from.
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 11 }

docsDevCmSwUpgradeCVCFailNotif NOTIFICATION-TYPE
    OBJECTS {
        docsDevEvLevel,
        docsDevEvId,
        docsDevEvText,
        ifPhysAddress,
        docsIfCmCmtsAddress,
        docsIfDocsisBaseCapability,
        docsIfCmStatusDocsisOperMode,



        docsIfCmStatusModulationType
    }
    STATUS current
    DESCRIPTION
        "A notification to report that the verification of the
         code file has failed during a secure software upgrade
         attempt.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 12 }

docsDevCmTODFailNotif NOTIFICATION-TYPE
    OBJECTS {
        docsDevEvLevel,
        docsDevEvId,
        docsDevEvText,
        ifPhysAddress,
        docsIfCmCmtsAddress,
        docsDevServerTime,
        docsIfDocsisBaseCapability,
        docsIfCmStatusDocsisOperMode,
        docsIfCmStatusModulationType
    }
    STATUS current
    DESCRIPTION
        "A notification to report the failure of a time of day



         operation.

         This notification sends additional information about
         the event by including the following objects in its
         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsDevServerTime: the IP address of the time server.
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 13 }

docsDevCmDCCReqFailNotif NOTIFICATION-TYPE
    OBJECTS {
        docsDevEvLevel,
        docsDevEvId,
        docsDevEvText,
        ifPhysAddress,
        docsIfCmCmtsAddress,
        docsIfDocsisBaseCapability,
        docsIfCmStatusDocsisOperMode,
        docsIfCmStatusModulationType
    }
    STATUS current
    DESCRIPTION
        " A notification to report the failure of a dynamic channel
         change request during the dynamic channel change process
         on the CM.

         This notification sends additional information about
         the event by including the following objects in its
         varbinding list.



         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is
           connected).
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 14 }

docsDevCmDCCRspFailNotif NOTIFICATION-TYPE
    OBJECTS {
        docsDevEvLevel,
        docsDevEvId,
        docsDevEvText,
        ifPhysAddress,
        docsIfCmCmtsAddress,
        docsIfDocsisBaseCapability,
        docsIfCmStatusDocsisOperMode,
        docsIfCmStatusModulationType
    }
    STATUS current
    DESCRIPTION
        "A notification to report the failure of a dynamic channel
         change response during the dynamic channel
         change process on the CM.

         This notification sends additional information about
         the event by including the following objects in its
         varbinding list.
         - docsDevEvLevel: the priority level associated with the
           event.
         - docsDevEvId: the unique identifier of the event that
           occurred.
         - docsDevEvText: a textual description of the event.
         - ifPhysAddress: the MAC address of the cable



           interface of this cable modem.
         - docsIfCmCmtsAddress: the MAC address of the CMTS
           to which the CM is connected (if there is a cable
           card/interface in the CMTS, then it is actually the
           MAC address of the cable interface to which it is
           connected).
         - docsIfDocsisBaseCapability: the highest
           version of the DOCSIS specification (1.0, 1.1, 2.0)
           that the device is capable of supporting.
         - docsIfCmStatusDocsisOperMode: the QOS level (1.0, 1.1)
           that the CM is operating in.
         - docsIfCmStatusModulationType: the upstream modulation
           methodology used by the CM.
        "
    ::= { docsDevCmNotifs 15 }

docsDevCmDCCAckFailNotif NOTIFICATION-TYPE
    OBJECTS {
        docsDevEvLevel,
        docsDevEvId,
        docsDevEvText,
        ifPhysAddress,
        docsIfCmCmtsAddress,
        docsIfDocsisBaseCapability,
        docsIfCmStatusDocsisOperMode,
        docsIfCmStatusModulationType
    }
    STATUS current
    DESCRIPTION
        "A notification to report the failure of a dynamic channel
         change acknowledgement during the dynamic channel
         change process on the CM.

         This notification sends additional information about
         the event by including the following objects in its

         varbinding list.
         - docsDevEvLevel: the priority level associated with the
           event.
         - docsDevEvId: the unique identifier of the event that
           occurred.
         - docsDevEvText: a textual description of the event.
         - ifPhysAddress: the MAC address of the cable
           interface of this cable modem.
         - docsIfCmCmtsAddress: the MAC address of the CMTS
           to which the CM is connected (if there is a cable
           card/interface in the CMTS, then it is actually the
           MAC address of the cable interface to which it is



           connected).
         - docsIfDocsisBaseCapability: the highest
           version of the DOCSIS specification (1.0, 1.1, 2.0)
           that the device is capable of supporting.
         - docsIfCmStatusDocsisOperMode: the QOS level (1.0, 1.1)
           that the CM is operating in.
         - docsIfCmtsCmStatusModulationType the upstream modulation
           methodology used by the CM.
        "
    ::= { docsDevCmNotifs 16}

docsDevCmtsInitRegReqFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a registration
         request from a CM during the CM initialization
         process that was detected on the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.



         - docsIfCmtsCmStatusModulationType: the upstream
           modulation methodology used by the CM.
        "
    ::= { docsDevCmtsNotifs 1 }

docsDevCmtsInitRegRspFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a registration
         response during the CM initialization
         process that was detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 2 }

docsDevCmtsInitRegAckFailNotif NOTIFICATION-TYPE



    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a registration
         acknowledgement from the CM during the CM
         initialization process that was detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 3 }

docsDevCmtsDynServReqFailNotif NOTIFICATION-TYPE
    OBJECTS {
        docsDevEvLevel,
        docsDevEvId,
        docsDevEvText,
        docsIfCmtsCmStatusMacAddress,
        ifPhysAddress,



        docsIfCmtsCmStatusDocsisRegMode,
        docsIfDocsisBaseCapability,
        docsIfCmtsCmStatusModulationType
     }
    STATUS current
    DESCRIPTION
        "A notification to report the failure of a dynamic service
         request during the dynamic services process
         that was detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 4 }

docsDevCmtsDynServRspFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION



        "A notification to report the failure of a dynamic service
         response during the dynamic services process
         that was detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 5 }

docsDevCmtsDynServAckFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a dynamic service
         acknowledgement during the dynamic services
         process that was detected by the CMTS.

         This notification sends additional information about
         the event by including the following objects in its



         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 6 }


docsDevCmtsBpiInitNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a BPI
         initialization attempt during the CM registration process
         that was detected by the CMTS.

         This notification sends additional information about
         the event by including the following objects in its
         varbinding list.
         - docsDevEvLevel: the priority level associated with the
           event.
         - docsDevEvId: the unique identifier of the event that
           occurred.



         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 7 }

docsDevCmtsBPKMNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a BPKM operation
         that is detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface



           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 8 }

docsDevCmtsDynamicSANotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a dynamic security
         association operation that is detected by the CMTS.

         This notification sends additional information about
         the event by including the following objects in its
         varbinding list.

         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.



         - docsIfCmtsCmStatusModulationType: the upstream
           modulation methodology used by the CM.
        "
    ::= { docsDevCmtsNotifs 9 }

docsDevCmtsDCCReqFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a dynamic channel
         change request during the dynamic channel
         change process and is detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 10 }

docsDevCmtsDCCRspFailNotif NOTIFICATION-TYPE



    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a dynamic channel
         change response during the dynamic channel
         change process and is detected by the CMTS.

         This notification sends additional information about
         the event by including the following objects in its
         varbinding list.
         - docsDevEvLevel: the priority level associated with the
           event.
         - docsDevEvId: the unique identifier of the event that
           occurred.
         - docsDevEvText: a textual description of the event.

         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 11 }

docsDevCmtsDCCAckFailNotif NOTIFICATION-TYPE
    OBJECTS {
        docsDevEvLevel,
        docsDevEvId,
        docsDevEvText,
        docsIfCmtsCmStatusMacAddress,



        ifPhysAddress,
        docsIfCmtsCmStatusDocsisRegMode,
        docsIfDocsisBaseCapability,
        docsIfCmtsCmStatusModulationType
    }
    STATUS current
    DESCRIPTION
        "A notification to report the failure of a dynamic channel
         change acknowledgement during the dynamic channel
         change process and is detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 12}

--
--Conformance definitions
--

docsDevNotifConformance OBJECT IDENTIFIER
   ::= { docsDevNotifMIB 4 }
docsDevNotifGroups OBJECT IDENTIFIER
   ::= { docsDevNotifConformance 1 }
docsDevNotifCompliances OBJECT IDENTIFIER
   ::= { docsDevNotifConformance 2 }
docsDevCmNotifCompliance MODULE-COMPLIANCE
    STATUS current



    DESCRIPTION
    "The compliance statement for CM Notifications and Control."

    MODULE --docsDevNotif
      MANDATORY-GROUPS {
               docsDevCmNotifControlGroup,
               docsDevCmNotificationGroup
           }
    ::= { docsDevNotifCompliances 1 }

docsDevCmNotifControlGroup OBJECT-GROUP
    OBJECTS {
        docsDevCmNotifControl
    }
    STATUS current
    DESCRIPTION
        "This group represents objects that allow control
         over CM Notifications."
    ::= { docsDevNotifGroups 1 }

docsDevCmNotificationGroup NOTIFICATION-GROUP
    NOTIFICATIONS {
        docsDevCmInitTLVUnknownNotif,
        docsDevCmDynServReqFailNotif,
        docsDevCmDynServRspFailNotif,
        docsDevCmDynServAckFailNotif,
        docsDevCmBpiInitNotif,
        docsDevCmBPKMNotif,
        docsDevCmDynamicSANotif,
        docsDevCmDHCPFailNotif,
        docsDevCmSwUpgradeInitNotif,
        docsDevCmSwUpgradeFailNotif,
        docsDevCmSwUpgradeSuccessNotif,
        docsDevCmSwUpgradeCVCFailNotif,
        docsDevCmTODFailNotif,
        docsDevCmDCCReqFailNotif,
        docsDevCmDCCRspFailNotif,
        docsDevCmDCCAckFailNotif
    }
    STATUS current
    DESCRIPTION
        "A collection of CM notifications providing device status
   and control."
    ::= { docsDevNotifGroups 2 }

docsDevCmtsNotifCompliance MODULE-COMPLIANCE
    STATUS current
    DESCRIPTION



        "The compliance statement for DOCSIS CMTS Notification
         and Control."
    MODULE --docsDevNotif
       MANDATORY-GROUPS {
          docsDevCmtsNotifControlGroup,
          docsDevCmtsNotificationGroup
       }
    ::= { docsDevNotifCompliances 2 }

docsDevCmtsNotifControlGroup OBJECT-GROUP
    OBJECTS {
        docsDevCmtsNotifControl
    }
    STATUS current
    DESCRIPTION
        "This group represents objects that allow control
         over CMTS Notifications."
    ::= { docsDevNotifGroups 3 }

docsDevCmtsNotificationGroup NOTIFICATION-GROUP
    NOTIFICATIONS {
        docsDevCmtsInitRegReqFailNotif,
        docsDevCmtsInitRegRspFailNotif,
        docsDevCmtsInitRegAckFailNotif ,
        docsDevCmtsDynServReqFailNotif,
        docsDevCmtsDynServRspFailNotif,
        docsDevCmtsDynServAckFailNotif,
        docsDevCmtsBpiInitNotif,
        docsDevCmtsBPKMNotif,
        docsDevCmtsDynamicSANotif,
        docsDevCmtsDCCReqFailNotif,
        docsDevCmtsDCCRspFailNotif,
        docsDevCmtsDCCAckFailNotif
    }
    STATUS current
    DESCRIPTION
        "A collection of CMTS notifications providing device
         status and control."
    ::= { docsDevNotifGroups 4 }

END
