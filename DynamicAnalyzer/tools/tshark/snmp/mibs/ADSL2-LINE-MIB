ADSL2-LINE-MIB DEFINITIONS ::= BEGIN

IMPORTS
   MODULE-IDENTITY,
   OBJECT-TYPE,
   transmission,
   Unsigned32,
   NOTIFICATION-TYPE,
   Integer32,
   Counter32
      FROM SNMPv2-SMI

   ifIndex
      FROM IF-MIB

   TruthValue,
   RowStatus
      FROM SNMPv2-TC

   SnmpAdminString
      FROM SNMP-FRAMEWORK-MIB

   HCPerfIntervalThreshold,
   HCPerfTimeElapsed
      FROM  HC-PerfHist-TC-MIB   -- [RFC3705]

   Adsl2Unit,
   Adsl2Direction,
   Adsl2TransmissionModeType,
   Adsl2RaMode,
   Adsl2InitResult,
   Adsl2OperationModes,
   Adsl2PowerMngState,
   Adsl2ConfPmsForce,
   Adsl2LConfProfPmMode,
   Adsl2LineLdsf,
   Adsl2LdsfResult,
   Adsl2SymbolProtection,
   Adsl2MaxBer,
   Adsl2ScMaskDs,
   Adsl2ScMaskUs,
   Adsl2RfiDs,
   Adsl2PsdMaskDs,
   Adsl2PsdMaskUs,
   Adsl2Tssi,
   Adsl2LastTransmittedState,
   Adsl2LineStatus,
   Adsl2ChAtmStatus,


   Adsl2ChPtmStatus
          FROM   ADSL2-LINE-TC-MIB       -- [This document]

   MODULE-COMPLIANCE,
   OBJECT-GROUP,
   NOTIFICATION-GROUP
      FROM SNMPv2-CONF;

adsl2MIB MODULE-IDENTITY
   LAST-UPDATED "200610040000Z" -- October 4th, 2006
   ORGANIZATION "ADSLMIB Working Group"
   CONTACT-INFO "WG-email:  adslmib@ietf.org
   Info:      https://www1.ietf.org/mailman/listinfo/adslmib


             Chair:     Mike Sneed
                        Sand Channel Systems
             Postal:    P.O. Box 37324
                        Raleigh NC 27627-732
             Email:     sneedmike@hotmail.com
             Phone:     +1 206 600 7022

             Co-Chair & Co-editor:
                        Menachem Dodge
                        ECI Telecom Ltd.
             Postal:    30 Hasivim St.
                        Petach Tikva 49517,
                        Israel.
             Email:     mbdodge@ieee.org
             Phone:     +972 3 926 8421

             Co-editor: Moti Morgenstern
                        ECI Telecom Ltd.
             Postal:    30 Hasivim St.
                        Petach Tikva 49517,
                        Israel.
             Email:     moti.morgenstern@ecitele.com
             Phone:     +972 3 926 6258

             Co-editor: Scott Baillie
                        NEC Australia
             Postal:    649-655 Springvale Road,
                        Mulgrave, Victoria 3170,
                        Australia.
             Email:     scott.baillie@nec.com.au
             Phone:     +61 3 9264 3986

             Co-editor: Umberto Bonollo


                        NEC Australia
             Postal:    649-655 Springvale Road,
                        Mulgrave, Victoria 3170,
                        Australia.
             Email:     umberto.bonollo@nec.com.au
             Phone:     +61 3 9264 3385
            "
   DESCRIPTION
        "
         This document defines a Management Information Base (MIB)
         module for use with network management protocols in the
         Internet community for the purpose of managing ADSL, ADSL2,
         and ADSL2+ lines.  The MIB module described in RFC 2662
         [RFC2662] describes objects used for managing Asymmetric
         Bit-Rate DSL (ADSL) interfaces per [T1E1.413], [G.992.1],
         and [G.992.2].  These object descriptions are based upon the
         specifications for the ADSL Embedded Operations Channel
         (EOC) as defined in American National Standards Institute
         (ANSI) T1E1.413/1995 [T1E1.413] and International
         Telecommunication Union (ITU-T) G.992.1  [G.992.1] and
         G.992.2 [G.992.2].

         This document does not obsolete RFC 2662 [RFC2662], but
         rather provides a more comprehensive management model that
         includes the ADSL2 and ADSL2+ technologies per G.992.3,
         G.992.4, and G.992.5 ([G.992.3], [G.992.4], and [G.992.5],
         respectively).  In addition, objects have been added to
         improve the management of ADSL, ADSL2, and ADSL2+ lines.

        Additionally, the management framework for New Generation
        ADSL lines specified by the Digital Subscriber Line Forum
        (DSLF) has been taken into consideration [TR-90].  That
        framework is based on ITU-T G.997.1 standard [G.997.1] as
        well as two amendments: [G.997.1am1] and [G.997.1am2].

        Note that the revised ITU-T G.997.1 standard also refers to
        the next generation of VDSL technology, known as VDSL2, per
        ITU-T G.993.2 [G.993.2].  However, managing VDSL2 lines is
        currently beyond the scope of this document.

        The MIB module is located in the MIB tree under MIB 2
        transmission, as discussed in the IANA Considerations section
        of this document.

        Copyright (C) The Internet Society (2006).  This version of
        this MIB module is part of RFC 4706: see the RFC itself for
        full legal notices."



   REVISION "200610040000Z" -- October 4th, 2006
   DESCRIPTION "Initial version, published as RFC 4706."
      ::= { transmission 238 }

  adsl2            OBJECT IDENTIFIER ::= { adsl2MIB 1 }
  ------------------------------------------------
  adsl2Line          OBJECT IDENTIFIER ::= { adsl2 1 }
  adsl2Status        OBJECT IDENTIFIER ::= { adsl2 2 }
  adsl2Inventory     OBJECT IDENTIFIER ::= { adsl2 3 }
  adsl2PM            OBJECT IDENTIFIER ::= { adsl2 4 }
  adsl2Profile       OBJECT IDENTIFIER ::= { adsl2 5 }
  adsl2Scalar        OBJECT IDENTIFIER ::= { adsl2 6 }
  adsl2Notifications OBJECT IDENTIFIER ::= { adsl2 0 }
  adsl2Conformance   OBJECT IDENTIFIER ::= { adsl2 7 }
  ------------------------------------------------
  adsl2PMLine      OBJECT IDENTIFIER ::= { adsl2PM 1 }
  adsl2PMChannel   OBJECT IDENTIFIER ::= { adsl2PM 2 }
  ------------------------------------------------
  adsl2ProfileLine      OBJECT IDENTIFIER ::= { adsl2Profile 1 }
  adsl2ProfileChannel   OBJECT IDENTIFIER ::= { adsl2Profile 2 }
  adsl2ProfileAlarmConf OBJECT IDENTIFIER ::= { adsl2Profile 3 }
  ------------------------------------------------
  adsl2ScalarSC         OBJECT IDENTIFIER ::= { adsl2Scalar 1 }
  ------------------------------------------------


------------------------------------------------
--          adsl2LineTable                    --
------------------------------------------------
adsl2LineTable  OBJECT-TYPE
   SYNTAX      SEQUENCE  OF  Adsl2LineEntry
   MAX-ACCESS  not-accessible
   STATUS      current
   DESCRIPTION
      "The table adsl2LineTable contains configuration,
       command, and status parameters of the ADSL2 line.
       The index of this table is an interface index where the
       interface has an ifType of adsl2plus(238).

       Several objects in this table MUST be maintained in a
       persistent manner."
   ::= { adsl2Line 1 }

adsl2LineEntry  OBJECT-TYPE
   SYNTAX      Adsl2LineEntry
   MAX-ACCESS  not-accessible
   STATUS      current
   DESCRIPTION


      "The table adsl2LineTable contains configuration,
      commands, and status parameters of the ADSL2 line"
   INDEX  { ifIndex }
   ::= { adsl2LineTable 1 }

Adsl2LineEntry  ::=
   SEQUENCE {
      adsl2LineCnfgTemplate            SnmpAdminString,
      adsl2LineAlarmCnfgTemplate       SnmpAdminString,
      adsl2LineCmndConfPmsf            Adsl2ConfPmsForce,
      adsl2LineCmndConfLdsf            Adsl2LineLdsf,
      adsl2LineCmndConfLdsfFailReason  Adsl2LdsfResult,
      adsl2LineCmndAutomodeColdStart   TruthValue,
      adsl2LineStatusAtuTransSys       Adsl2TransmissionModeType,
      adsl2LineStatusPwrMngState       Adsl2PowerMngState,
      adsl2LineStatusInitResult        Adsl2InitResult,
      adsl2LineStatusLastStateDs       Adsl2LastTransmittedState,
      adsl2LineStatusLastStateUs       Adsl2LastTransmittedState,
      adsl2LineStatusAtur              Adsl2LineStatus,
      adsl2LineStatusAtuc              Adsl2LineStatus,
      adsl2LineStatusLnAttenDs         Unsigned32,
      adsl2LineStatusLnAttenUs         Unsigned32,
      adsl2LineStatusSigAttenDs        Unsigned32,
      adsl2LineStatusSigAttenUs        Unsigned32,
      adsl2LineStatusSnrMarginDs       Integer32,
      adsl2LineStatusSnrMarginUs       Integer32,
      adsl2LineStatusAttainableRateDs  Unsigned32,
      adsl2LineStatusAttainableRateUs  Unsigned32,
      adsl2LineStatusActPsdDs          Integer32,
      adsl2LineStatusActPsdUs          Integer32,
      adsl2LineStatusActAtpDs          Integer32,
      adsl2LineStatusActAtpUs          Integer32
   }

adsl2LineCnfgTemplate  OBJECT-TYPE
   SYNTAX      SnmpAdminString (SIZE(1..32))
   MAX-ACCESS  read-write
   STATUS      current
   DESCRIPTION
      "The value of this object identifies the row in the ADSL2 Line
       Configuration Templates Table, (adsl2LineConfTemplateTable),
       which applies for this ADSL2 line.

       This object MUST be maintained in a persistent manner."
   REFERENCE    "DSL Forum TR-90, paragraph 5.1.1"
   DEFVAL       { "DEFVAL" }
   ::= { adsl2LineEntry 1 }



adsl2LineAlarmCnfgTemplate  OBJECT-TYPE
   SYNTAX      SnmpAdminString (SIZE(1..32))
   MAX-ACCESS  read-write
   STATUS      current
   DESCRIPTION
      "The value of this object identifies the row in the ADSL2 Line
      Alarm Configuration Template Table,
      (adsl2LineAlarmConfTemplateTable), which applies to this ADSL2
      line.

      This object MUST be maintained in a persistent manner."
   REFERENCE    "DSL Forum TR-90, paragraph 5.1.1"
   DEFVAL       { "DEFVAL" }
   ::= { adsl2LineEntry 2 }

adsl2LineCmndConfPmsf  OBJECT-TYPE
   SYNTAX      Adsl2ConfPmsForce
   MAX-ACCESS  read-write
   STATUS      current
   DESCRIPTION
      "Power management state forced.  Defines the line states to be
       forced by the near-end ATU on this line.  The various possible
       values are:
          l3toL0(0),
          l0toL2(2), or
          l0orL2toL3(3).

       This object MUST be maintained in a persistent manner."
   REFERENCE    "ITU-T G.997.1, paragraph 7.3.1.1.3"
   DEFVAL       { l3toL0 }
   ::= { adsl2LineEntry 3 }

adsl2LineCmndConfLdsf  OBJECT-TYPE
   SYNTAX      Adsl2LineLdsf
   MAX-ACCESS  read-write
   STATUS      current
   DESCRIPTION
      "Loop diagnostics mode forced (LDSF).  Defines whether the line
       should be forced into the loop diagnostics mode by the
       near-end ATU on this line or only be responsive to loop
       diagnostics initiated by the far-end ATU.

       This object MUST be maintained in a persistent manner.
       However, in case the operator forces loop diagnostics mode
       then the access node should reset the object (inhibit) when
       loop diagnostics mode procedures are completed."
   REFERENCE    "ITU-T G.997.1, paragraph 7.3.1.1.8"
   DEFVAL       { inhibit }


   ::= { adsl2LineEntry 4 }

adsl2LineCmndConfLdsfFailReason  OBJECT-TYPE
   SYNTAX      Adsl2LdsfResult
   MAX-ACCESS  read-only
   STATUS      current
   DESCRIPTION
      "The status of the recent occasion the Loop diagnostics mode
       forced (LDSF) was issued for the associated line.  Possible
       values are:
          none(1)         - The default value in case LDSF was never
                            requested for the associated line.
          success(2)      - The recent command completed
                            successfully.
          inProgress(3)   - The Loop Diagnostics process is in
                            progress.
          unsupported(4)  - The NE or the line card doesn't support
                            LDSF.
          cannotRun(5)    - The NE cannot initiate the command, due
                            to a nonspecific reason.
          aborted(6)      - The Loop Diagnostics process aborted.
          failed(7)       - The Loop Diagnostics process failed.
          illegalMode(8)  - The NE cannot initiate the command, due
                            to the specific mode of the relevant
                            line.
          adminUp(9)      - The NE cannot initiate the command, as
                            the relevant line is administratively
                            'Up'.
          tableFull(10)   - The NE cannot initiate the command, due
                            to reaching the maximum number of rows
                            in the results table.
          noResources(11) - The NE cannot initiate the command, due
                            to lack of internal memory resources."
   DEFVAL       { none }
   ::= { adsl2LineEntry 5 }

   adsl2LineCmndAutomodeColdStart   OBJECT-TYPE
      SYNTAX      TruthValue
      MAX-ACCESS  read-write
      STATUS      current
      DESCRIPTION
         "Automode cold start forced.  This parameter is defined
          in order to improve testing of the performance of ATUs
          supporting automode when it is enabled in the MIB.
          Change the value of this parameter to 'true' indicates
          a change in loop conditions applied to the devices under
          test.  The ATUs shall reset any historical information
          used for automode and for shortening G.994.1 handshake


          and initialization.

          Automode is the case where multiple operation-modes are
          enabled through the adsl2LConfProfAtuTransSysEna object
          in the line configuration profile being used for the
          ADSL line, and where the selection of the actual
          operation-mode depends not only on the common
          capabilities of both ATUs (as exchanged in G.994.1), but
          also on achievable data rates under given loop
          conditions.

          This object MUST be maintained in a persistent manner."

      REFERENCE    "ITU-T G.997.1 (amendment 1), 7.3.1.1.10"
      DEFVAL       { false }
      ::= { adsl2LineEntry 6 }


adsl2LineStatusAtuTransSys  OBJECT-TYPE
   SYNTAX      Adsl2TransmissionModeType
   MAX-ACCESS  read-only
   STATUS      current
   DESCRIPTION
      "The ATU Transmission System (ATS) in use.
       It is coded in a bit-map representation with only a single bit
       set to '1' (the selected coding for the ADSL line).  This
       parameter may be derived from the handshaking procedures
       defined in Recommendation G.994.1.  A set of ADSL2 line
       transmission modes, with one bit per mode."
   REFERENCE    "ITU-T G.997.1, paragraph 7.3.1.1.1"
   ::= { adsl2LineEntry 7 }

adsl2LineStatusPwrMngState  OBJECT-TYPE
   SYNTAX      Adsl2PowerMngState
   MAX-ACCESS  read-only
   STATUS      current
   DESCRIPTION
      "The current power management state.  One of four possible
       power management states:
          L0 - Synchronized and full transmission (i.e., Showtime).
          L1 - Low Power with reduced net data rate (G.992.2 only).
          L2 - Low Power with reduced net data rate (G.992.3 and
               G.992.4 only).
          L3 - No power.
      The various possible values are: l0(1), l1(2), l2(3), or
      l3(4)."
   REFERENCE    "ITU-T G.997.1, paragraph 7.5.1.2"
      ::= { adsl2LineEntry 8 }


adsl2LineStatusInitResult  OBJECT-TYPE
   SYNTAX      Adsl2InitResult
   MAX-ACCESS  read-only
   STATUS      current
   DESCRIPTION
      "Indicates the result of the last full initialization performed
       on the line.  It is an enumeration type with the following
       values: noFail(0), configError(1), configNotFeasible(2),
       commFail(3), noPeerAtu(4), or otherCause(5)."
   REFERENCE    "ITU-T G.997.1, paragraph 7.5.1.3"
   ::= { adsl2LineEntry 9 }

adsl2LineStatusLastStateDs  OBJECT-TYPE
   SYNTAX      Adsl2LastTransmittedState
   MAX-ACCESS  read-only
   STATUS      current
   DESCRIPTION
      "The last successful transmitted initialization state in
       the downstream direction in the last full initialization
       performed on the line."
   REFERENCE    "ITU-T G.997.1, paragraph 7.5.1.4"
   ::= { adsl2LineEntry 10 }

adsl2LineStatusLastStateUs  OBJECT-TYPE
   SYNTAX      Adsl2LastTransmittedState
   MAX-ACCESS  read-only
   STATUS      current
   DESCRIPTION
      "The last successful transmitted initialization state in the
       upstream direction in the last full initialization performed
       on the line."
   REFERENCE    "ITU-T G.997.1, paragraph 7.5.1.5"
   ::= { adsl2LineEntry 11 }

adsl2LineStatusAtur  OBJECT-TYPE
   SYNTAX      Adsl2LineStatus
   MAX-ACCESS  read-only
   STATUS      current
   DESCRIPTION
      "Indicates current state (existing failures) of the ATU-R.
       This is a bit-map of possible conditions."
   REFERENCE    "ITU-T G.997.1, paragraph 7.1.1.2"
   ::= { adsl2LineEntry 12 }

adsl2LineStatusAtuc  OBJECT-TYPE
   SYNTAX      Adsl2LineStatus
   MAX-ACCESS  read-only
   STATUS      current


   DESCRIPTION
      "Indicates current state (existing failures) of the ATU-C.
       This is a bit-map of possible conditions."
   REFERENCE    "ITU-T G.997.1, paragraph 7.1.1.1"
   ::= { adsl2LineEntry 13 }

adsl2LineStatusLnAttenDs  OBJECT-TYPE
   SYNTAX      Unsigned32 (0..1270 | 2147483646 | 2147483647)
   UNITS       "0.1 dB"
   MAX-ACCESS  read-only
   STATUS      current
   DESCRIPTION
      "The measured difference in the total power transmitted by the
       ATU-C and the total power received by the ATU-R over all sub-
       carriers during diagnostics mode and initialization.  It
       ranges from 0 to 1270 units of 0.1 dB (physical values
       are 0 to 127 dB).
       A special value of 0x7FFFFFFF (2147483647) indicates the line
       attenuation is out of range to be represented.
       A special value of 0x7FFFFFFE (2147483646) indicates the line
       attenuation measurement is currently unavailable."
   REFERENCE    "ITU-T G.997.1, paragraph 7.5.1.6"
   ::= { adsl2LineEntry 14 }

adsl2LineStatusLnAttenUs  OBJECT-TYPE
   SYNTAX      Unsigned32 (0..1270 | 2147483646 | 2147483647)
   UNITS       "0.1 dB"
   MAX-ACCESS  read-only
   STATUS      current
   DESCRIPTION
      "The measured difference in the total power transmitted by the
       ATU-R and the total power received by the ATU-C over all sub-
       carriers during diagnostics mode and initialization.
       It ranges from 0 to 1270 units of 0.1 dB (physical values are
       0 to 127 dB).
       A special value of 0x7FFFFFFF (2147483647) indicates the line
       attenuation is out of range to be represented.
       A special value of 0x7FFFFFFE (2147483646) indicates the line
       attenuation measurement is currently unavailable."
   REFERENCE    "ITU-T G.997.1, paragraph 7.5.1.7"
   ::= { adsl2LineEntry 15 }

adsl2LineStatusSigAttenDs  OBJECT-TYPE
   SYNTAX      Unsigned32 (0..1270 | 2147483646 | 2147483647)
   UNITS       "0.1 dB"
   MAX-ACCESS  read-only
   STATUS      current
   DESCRIPTION


      "The measured difference in the total power transmitted by the
       ATU-C and the total power received by the ATU-R over all sub-
       carriers during Showtime.  It ranges from 0 to 1270 units of
       0.1 dB (physical values are 0 to 127 dB).
       A special value of 0x7FFFFFFF (2147483647) indicates the
       signal attenuation is out of range to be represented.
       A special value of 0x7FFFFFFE (2147483646) indicates the
       signal attenuation measurement is currently unavailable."
   REFERENCE    "ITU-T G.997.1, paragraph 7.5.1.8"
   ::= { adsl2LineEntry 16 }

adsl2LineStatusSigAttenUs  OBJECT-TYPE
   SYNTAX      Unsigned32 (0..1270 | 2147483646 | 2147483647)
   UNITS       "0.1 dB"
   MAX-ACCESS  read-only
   STATUS      current
   DESCRIPTION
      "The measured difference in the total power transmitted by the
       ATU-R and the total power received by the ATU-C over all sub-
       carriers during Showtime.  It ranges from 0 to 1270 units of
       0.1 dB (physical values are 0 to 127 dB).
       A special value of 0x7FFFFFFF (2147483647) indicates the
       signal attenuation is out of range to be represented.
       A special value of 0x7FFFFFFE (2147483646) indicates the
       signal attenuation measurement is currently unavailable."
   REFERENCE    "ITU-T G.997.1, paragraph 7.5.1.9"
   ::= { adsl2LineEntry 17 }

adsl2LineStatusSnrMarginDs  OBJECT-TYPE
   SYNTAX      Integer32 (-640..630 | 2147483646 | 2147483647)
   UNITS       "0.1 dB"
   MAX-ACCESS  read-only
   STATUS      current
   DESCRIPTION
      "Downstream SNR Margin is the maximum increase in dB of the
       noise power received at the ATU-R, such that the BER
       requirements are met for all downstream bearer channels.  It
       ranges from -640 to 630 units of 0.1 dB (physical values are
       -64 to 63 dB).
       A special value of 0x7FFFFFFF (2147483647) indicates the
       SNR Margin is out of range to be represented.
       A special value of 0x7FFFFFFE (2147483646) indicates the
       SNR Margin measurement is currently unavailable."
   REFERENCE    "ITU-T G.997.1, paragraph 7.5.1.10"
   ::= { adsl2LineEntry 18 }

adsl2LineStatusSnrMarginUs  OBJECT-TYPE
   SYNTAX      Integer32 (-640..630 | 2147483646 | 2147483647)


   UNITS       "0.1 dB"
   MAX-ACCESS  read-only
   STATUS      current
   DESCRIPTION
      "Upstream SNR Margin is the maximum increase in dB of the noise
       power received at the ATU-C, such that the BER requirements
       are met for all downstream bearer channels.  It ranges from
       -640 to 630 units of 0.1 dB (physical values are -64 to
       63 dB).
       A special value of 0x7FFFFFFF (2147483647) indicates the
       SNR Margin is out of range to be represented.
       A special value of 0x7FFFFFFE (2147483646) indicates the
       SNR Margin measurement is currently unavailable."
   REFERENCE    "ITU-T G.997.1, paragraph 7.5.1.11"
   ::= { adsl2LineEntry 19 }

adsl2LineStatusAttainableRateDs  OBJECT-TYPE
   SYNTAX      Unsigned32
   UNITS       "bits/second"
   MAX-ACCESS  read-only
   STATUS      current
   DESCRIPTION
      "Maximum Attainable Data Rate Downstream.
       The maximum downstream net data rate currently attainable by
       the ATU-C transmitter and the ATU-R receiver, coded in
       bits/second."
   REFERENCE    "ITU-T G.997.1, paragraph 7.5.1.12"
   ::= { adsl2LineEntry 20 }

adsl2LineStatusAttainableRateUs  OBJECT-TYPE
   SYNTAX      Unsigned32
   UNITS       "bits/second"
   MAX-ACCESS  read-only
   STATUS      current
   DESCRIPTION
      "Maximum Attainable Data Rate Upstream.
       The maximum upstream net data rate currently attainable by the
       ATU-R transmitter and the ATU-C receiver, coded in
       bits/second."
   REFERENCE    "ITU-T G.997.1, paragraph 7.5.1.13"
   ::= { adsl2LineEntry 21 }

adsl2LineStatusActPsdDs OBJECT-TYPE
   SYNTAX      Integer32 (-900..0 | 2147483647)
   UNITS       "0.1 dB"
   MAX-ACCESS  read-only
   STATUS      current
   DESCRIPTION


      "Actual Power Spectrum Density (PSD) Downstream.  The average
       downstream transmit PSD over the sub-carriers used for
       downstream.  It ranges from -900 to 0 units of 0.1 dB
       (physical values are -90 to 0 dBm/Hz).
       A value of 0x7FFFFFFF (2147483647) indicates the measurement
       is out of range to be represented."
   REFERENCE    "ITU-T G.997.1, paragraph 7.5.1.14"
   ::= { adsl2LineEntry 22 }

adsl2LineStatusActPsdUs OBJECT-TYPE
   SYNTAX      Integer32 (-900..0 | 2147483647)
   UNITS       "0.1 dB"
   MAX-ACCESS  read-only
   STATUS      current
   DESCRIPTION
      "Actual Power Spectrum Density (PSD) Upstream.  The average
       upstream transmit PSD over the sub-carriers used for upstream.
       It ranges from -900 to 0 units of 0.1 dB (physical values
       are -90 to 0 dBm/Hz).
       A value of 0x7FFFFFFF (2147483647) indicates the measurement
       is out of range to be represented."
   REFERENCE    "ITU-T G.997.1, paragraph 7.5.1.15"
   ::= { adsl2LineEntry 23 }

adsl2LineStatusActAtpDs  OBJECT-TYPE
   SYNTAX      Integer32 (-310..310 | 2147483647)
   UNITS       "0.1 dB"
   MAX-ACCESS  read-only
   STATUS      current
   DESCRIPTION
      "Actual Aggregate Transmit Power Downstream.  The total amount
       of transmit power delivered by the ATU-C at the U-C reference
       point, at the instant of measurement.  It ranges from -310 to
       310 units of 0.1 dB (physical values are -31 to 31 dBm).
       A value of 0x7FFFFFFF (2147483647) indicates the measurement
       is out of range to be represented."
   REFERENCE    "ITU-T G.997.1, paragraph 7.5.1.16"
   ::= { adsl2LineEntry 24 }

adsl2LineStatusActAtpUs  OBJECT-TYPE
   SYNTAX      Integer32 (-310..310 | 2147483647)
   UNITS       "0.1 dB"
   MAX-ACCESS  read-only
   STATUS      current
   DESCRIPTION
      "Actual Aggregate Transmit Power Upstream.  The total amount of
       transmit power delivered by the ATU-R at the U-R
       reference point, at the instant of measurement.  It ranges


       from -310 to 310 units of 0.1 dB (physical values are -31
       to 31 dBm).
       A value of 0x7FFFFFFF (2147483647) indicates the measurement
       is out of range to be represented."
   REFERENCE    "ITU-T G.997.1, paragraph 7.5.1.17"
   ::= { adsl2LineEntry 25 }


------------------------------------------------
--        adsl2ChannelStatusTable             --
------------------------------------------------
adsl2ChannelStatusTable  OBJECT-TYPE
   SYNTAX      SEQUENCE  OF  Adsl2ChannelStatusEntry
   MAX-ACCESS  not-accessible
   STATUS      current
   DESCRIPTION
      "The table adsl2ChannelStatusTable contains status
       parameters of the ADSL2 channel.  This table contains live
       data from equipment."
   ::= { adsl2Status 1 }

adsl2ChannelStatusEntry  OBJECT-TYPE
   SYNTAX      Adsl2ChannelStatusEntry
   MAX-ACCESS  not-accessible
   STATUS      current
   DESCRIPTION
      "The table adsl2ChannelStatusTable contains status
       parameters of the ADSL2 channel.
       The index of this table consists of an interface index, where
       the interface has an ifType value that is applicable
       for a DSL channel, along with a termination unit."
   INDEX  { ifIndex, adsl2ChStatusUnit }
   ::= { adsl2ChannelStatusTable 1 }

Adsl2ChannelStatusEntry  ::=
   SEQUENCE {
      adsl2ChStatusUnit                Adsl2Unit,
      adsl2ChStatusChannelNum          Unsigned32,
      adsl2ChStatusActDataRate         Unsigned32,
      adsl2ChStatusPrevDataRate        Unsigned32,
      adsl2ChStatusActDelay            Unsigned32,
      adsl2ChStatusAtmStatus           Adsl2ChAtmStatus,
      adsl2ChStatusPtmStatus           Adsl2ChPtmStatus
   }

adsl2ChStatusUnit  OBJECT-TYPE
   SYNTAX      Adsl2Unit
   MAX-ACCESS  not-accessible


   STATUS      current
   DESCRIPTION
      "The termination unit atuc(1) or atur(2)."
   ::= { adsl2ChannelStatusEntry 1 }

adsl2ChStatusChannelNum  OBJECT-TYPE
   SYNTAX      Unsigned32
   MAX-ACCESS  read-only
   STATUS      current
   DESCRIPTION
      "Provides the bearer channel number associated with this
       row (i.e., the channel ifIndex).
       This enables determining the channel configuration profile
       and the channel thresholds profile applicable for this
       bearer channel."
   ::= { adsl2ChannelStatusEntry 2 }

adsl2ChStatusActDataRate  OBJECT-TYPE
   SYNTAX      Unsigned32(0..200000000)
   UNITS       "bits/second"
   MAX-ACCESS  read-only
   STATUS      current
   DESCRIPTION
      "The actual net data rate that the bearer channel is operating
       at, if in L0 power management state.  In L1 or L2 states, it
       relates to the previous L0 state.  The data rate is coded in
       bits/second."
   REFERENCE    "ITU-T G.997.1, paragraph 7.5.2.1"
   ::= { adsl2ChannelStatusEntry 3 }

adsl2ChStatusPrevDataRate  OBJECT-TYPE
   SYNTAX      Unsigned32(0..200000000)
   UNITS       "bits/second"
   MAX-ACCESS  read-only
   STATUS      current
   DESCRIPTION
      "The previous net data rate that the bearer channel was
       operating at just before the latest rate change event.  This
       could be a full or short initialization, fast retrain, DRA or
       power management transitions, excluding transitions between L0
       state and L1 or L2 states.  The data rate is coded in
       bits/second."
   REFERENCE    "ITU-T G.997.1, paragraph 7.5.2.2"
   ::= { adsl2ChannelStatusEntry 4 }

adsl2ChStatusActDelay  OBJECT-TYPE
   SYNTAX      Unsigned32(0..8176)
   UNITS       "milliseconds"


   MAX-ACCESS  read-only
   STATUS      current
   DESCRIPTION
      "The actual one-way interleaving delay introduced by the
       PMS-TC in the direction of the bearer channel, if in L0
       power management state.  In L1 or L2 states, it relates to
       the previous L0 state.  It is coded in ms (rounded to the
       nearest ms)."
   REFERENCE    "ITU-T G.997.1, paragraph 7.5.2.3"
   ::= { adsl2ChannelStatusEntry 5 }

adsl2ChStatusAtmStatus  OBJECT-TYPE
   SYNTAX      Adsl2ChAtmStatus
   MAX-ACCESS  read-only
   STATUS      current
   DESCRIPTION
      "Indicates the current state (existing failures) of the ADSL
       channel in case its Data Path is ATM.  This is a bit-map of
       possible conditions.  The various bit positions are:
          noDefect(0),
          noCellDelineation(1), or
          lossOfCellDelineation(2).
      In the case where the channel is not an ATM Data Path, the
      object is set to '0'."
   REFERENCE    "ITU-T G.997.1, paragraph 7.1.4"
   ::= { adsl2ChannelStatusEntry 6 }

adsl2ChStatusPtmStatus  OBJECT-TYPE
   SYNTAX      Adsl2ChPtmStatus
   MAX-ACCESS  read-only
   STATUS      current
   DESCRIPTION
      "Indicates the current state (existing failures) of the ADSL
       channel in case its Data Path is PTM.  This is a bit-map of
       possible conditions.  The various bit positions are:
          noDefect(0), or
          outOfSync(1).
      In the case where the channel is not a PTM Data Path, the
      object is set to '0'."
   REFERENCE    "ITU-T G.997.1, paragraph 7.1.5"
   ::= { adsl2ChannelStatusEntry 7 }


------------------------------------------------
--        Scalars that relate to the adsl2SCStatusTable.
------------------------------------------------

adsl2ScalarSCMaxInterfaces  OBJECT-TYPE



   SYNTAX      Unsigned32
   MAX-ACCESS  read-only
   STATUS      current
   DESCRIPTION
      "This value determines the upper size of adsl2SCStatusTable.
       The maximum number of entries in adsl2SCStatusTable is equal
       to two times the value of this attribute."
   ::= { adsl2ScalarSC 1 }

adsl2ScalarSCAvailInterfaces  OBJECT-TYPE
   SYNTAX      Unsigned32
   MAX-ACCESS  read-only
   STATUS      current
   DESCRIPTION
      "This value determines the amount of space that is
       currently available in adsl2SCStatusTable.
       The number of entries available in adsl2SCStatusTable is equal
       to two times the value of this attribute."
   ::= { adsl2ScalarSC 2 }

------------------------------------------------
--        adsl2SCStatusTable                --
------------------------------------------------

adsl2SCStatusTable  OBJECT-TYPE
   SYNTAX      SEQUENCE  OF  Adsl2SCStatusEntry
   MAX-ACCESS  not-accessible
   STATUS      current
   DESCRIPTION
      "The table adsl2SCStatusTable contains status parameters
       of the ADSL2 sub-carriers.  The following points apply to this
       table:
       1.  The main purpose of this table is to hold the results
           of a DELT.
       2.  This table also holds parameters obtained at line
           initialization time.
       3.  The rows in this table are volatile; that is, they are
           lost if the SNMP agent is rebooted.
       4.  Due to the large OCTET STRING attributes in this table,
           the worst case memory requirements for this table are
           very high.  The manager may use the row status attribute
           of this table to delete rows in order to reclaim memory.
       5.  The manager may create rows in this table.  The SNMP
           agent may create rows in this table.  Only the manager
           may delete rows in this table.
       6.  The maximum number of rows allowable in this table is
           indicated by the scalar attribute
           adsl2ScalarSCMaxInterfaces.



           The number of rows available in this table is indicated
           by the scalar attribute adsl2ScalarSCAvailInterfaces.
       7.  The SNMP agent is permitted to create rows in this table
           when a DELT completes successfully or when line
           initialization occurs.  It is not mandatory for the SNMP
           agent to create rows in this table; hence, it may be
           necessary for the manager to create rows in this table
           before any results can be stored.
       8.  If the manager attempts to create a row in this table
           and there are no more rows available, the creation
           attempt will fail, and the response to the SNMP SET PDU
           will contain the error noCreation(11).
       9.  If the SNMP agent attempts to create a row in this table
           and there are no more rows available, the creation
           attempt will fail, and the attribute
           adsl2LineCmndConfLdsfFailReason will indicate the
           reason for the failure.  The failure reason will be either
           tableFull(10) or noResources(11).
       10. An example of use of this table is as follows:
           Step 1. : The DELT is started by setting the
                   : adsl2LineCmndConfLdsf from inhibit to force.
           Step 2. : The DELT completes, and valid data is
                   : available.
           Step 3. : The row in the adsl2SCStatusTable where the
                   : results will be stored does not yet exist so
                   : the SNMP agent attempts to create the row.
           Step 4. : Due to a low memory condition, a row in the
                   : adsl2SCStatusTable table cannot be created at
                   : this time.
           Step 5. : The reason for the failure, tableFull(10), is
                   : indicated in the adsl2LineCmndConfLdsfFailReason
                   : attribute.
       11. Another example of use of this table is as follows :
           Step 1. : The DELT is started by setting the
                   : adsl2LineCmndConfLdsf from inhibit to force.
           Step 2. : The DELT completes and valid data is
                   : available.
           Step 3. : The row in the adsl2SCStatusTable where the
                   : results will be stored does not yet exist so
                   : the SNMP agent attempts to create the row.
           Step 4. : The row creation is successful.
           Step 5. : The value of the attribute
                   : adsl2LineCmndConfLdsfFailReasonreason is set
                   : to success(2).
       12. Another example of use of this table is as follows:
           Step 1. : The manager creates a row in adsl2SCStatusTable
                   : for a particular ADSL2 line.
           Step 2. : The DELT is started on the above-mentioned



                   : line by setting the adsl2LineCmndConfLdsf from
                   : inhibit to force.
           Step 3. : The DELT completes, and valid data is
                   : available.
           Step 4. : The value of the attribute
                   : adsl2LineCmndConfLdsfFailReasonreason is set
                   : to success(2)."
   ::= { adsl2Status 2 }

adsl2SCStatusEntry  OBJECT-TYPE
   SYNTAX      Adsl2SCStatusEntry
   MAX-ACCESS  not-accessible
   STATUS      current
   DESCRIPTION
      "The table Adsl2SCStatusEntry contains status parameters
       of the ADSL2 sub-carriers.
       The index of this table is an interface index where the
       interface has an ifType of adsl2plus(238)."
   INDEX  { ifIndex, adsl2SCStatusDirection }
   ::= { adsl2SCStatusTable 1 }

Adsl2SCStatusEntry  ::=
   SEQUENCE {
      adsl2SCStatusDirection         Adsl2Direction,
      adsl2SCStatusMtime             Unsigned32,
      adsl2SCStatusSnr               OCTET STRING,
      adsl2SCStatusBitsAlloc         OCTET STRING,
      adsl2SCStatusGainAlloc         OCTET STRING,
      adsl2SCStatusTssi              Adsl2Tssi,
      adsl2SCStatusLinScale          Unsigned32,
      adsl2SCStatusLinReal           OCTET STRING,
      adsl2SCStatusLinImg            OCTET STRING,
      adsl2SCStatusLogMt             Unsigned32,
      adsl2SCStatusLog               OCTET STRING,
      adsl2SCStatusQlnMt             Unsigned32,
      adsl2SCStatusQln               OCTET STRING,
      adsl2SCStatusLnAtten           Unsigned32,
      adsl2SCStatusSigAtten          Unsigned32,
      adsl2SCStatusSnrMargin         Integer32,
      adsl2SCStatusAttainableRate    Unsigned32,
      adsl2SCStatusActAtp            Integer32,
      adsl2SCStatusRowStatus         RowStatus
   }

adsl2SCStatusDirection  OBJECT-TYPE
   SYNTAX      Adsl2Direction
   MAX-ACCESS  not-accessible
   STATUS      current



   DESCRIPTION
     "The direction of the sub-carrier is either
     upstream or downstream."
     ::= { adsl2SCStatusEntry 1 }

adsl2SCStatusMtime  OBJECT-TYPE
   SYNTAX      Unsigned32
   UNITS       "symbols"
   MAX-ACCESS  read-only
   STATUS      current
   DESCRIPTION
     "SNR Measurement Time.  The number of symbols used to
      measure the SNR values on the respective transmission
      direction.  It should correspond to the value specified in the
      recommendation (e.g., the number of symbols in 1 second
      time interval for G.992.3).  This parameter corresponds to
      1 second in loop diagnostic procedure and should be updated
      otherwise."
   REFERENCE    "ITU-T G.997.1, paragraph 7.5.1.20.1 (SNRMTds)
                 and paragraph 7.5.1.20.3 (SNRMTus)"
     ::= { adsl2SCStatusEntry 2 }

adsl2SCStatusSnr  OBJECT-TYPE
   SYNTAX      OCTET STRING  (SIZE(0..512))
   MAX-ACCESS  read-only
   STATUS      current
   DESCRIPTION
     "The SNR Margin per sub-carrier, expressing the ratio between
      the received signal power and received noise power per
      subscriber.  It is an array of 512 octets, designed for
      supporting up to 512 (downstream) sub-carriers.
      The number of utilized octets on downstream direction depends
      on NSCds, and on upstream direction it depends on NSCus.  This
      value is referred to here as NSC.
      Octet i (0 <= i < NSC) is set to a value in the range 0 to
      254 to indicate that the respective downstream or upstream sub-
      carrier i has SNR of: (-32 + Adsl2SubcarrierSnr(i)/2) in dB
      (i.e., -32 to 95dB).
      The special value 255 means that no measurement could be done
      for the subcarrier because it is out of the PSD mask passband
      or that the noise PSD is out of range to be represented.
      Each value in this array is 8 bits wide."
   REFERENCE    "ITU-T G.997.1, paragraph 7.5.1.20.2 (SNRpsds)
                 and paragraph 7.5.1.20.4 (SNRpsus)"
     ::= { adsl2SCStatusEntry 3 }

adsl2SCStatusBitsAlloc  OBJECT-TYPE
   SYNTAX      OCTET STRING  (SIZE(0..256))



   UNITS       "bits"
   MAX-ACCESS  read-only
   STATUS      current
   DESCRIPTION
     "The bits allocation per sub-carrier.  An array of 256 octets
      (512 nibbles), designed for supporting up to 512 (downstream)
      sub-carriers.
      The number of utilized nibbles on downstream direction depends
      on NSCds, and on upstream direction it depends on NSCus.  This
      value is referred to here as NSC.
      Nibble i (0 <= i < NSC) is set to a value in the range 0
      to 15 to indicate that the respective downstream or upstream
      sub-carrier i has the same amount of bits allocation."
   REFERENCE    "ITU-T G.997.1, paragraph 7.5.1.21.1 (BITSpsds)
                 and paragraph 7.5.1.21.2 (BITSpsus)"
     ::= { adsl2SCStatusEntry 4 }

adsl2SCStatusGainAlloc  OBJECT-TYPE
   SYNTAX      OCTET STRING  (SIZE(0..1024))
   MAX-ACCESS  read-only
   STATUS      current
   DESCRIPTION
     "The gain allocation per sub-carrier.  An array of 512 16-bits
     values, designed for supporting up to 512 (downstream) sub-
     carriers.
     The number of utilized octets on downstream direction depends
     on NSCds, and on upstream direction it depends on NSCus.  This
     value is referred to here as NSC.
     Value i (0 <= i < NSC) is in the range 0 to 4093 to indicate
     that the respective downstream or upstream sub-carrier i has the
     same amount of gain value.
     The gain value is represented as a multiple of 1/512 on a
     linear scale.  Each value in this array is 16 bits wide and is
     stored in big endian format."
   REFERENCE    "ITU-T G.997.1, paragraph 7.5.1.21.3 (GAINSpsds)
                 and paragraph 7.5.1.21.4 (GAINSpsus)"
     ::= { adsl2SCStatusEntry 5 }

adsl2SCStatusTssi  OBJECT-TYPE
   SYNTAX      Adsl2Tssi
   MAX-ACCESS  read-only
   STATUS      current
   DESCRIPTION
     "The transmit spectrum shaping (TSSi) breakpoints expressed
     as the set of breakpoints exchanged during G.994.1.
     Each breakpoint is a pair of values occupying 3 octets with the
     following structure:
     First 2 octets - Index of the subcarrier used in the context of



                      the breakpoint.
     Third octet    - The shaping parameter at the breakpoint.
     Subcarrier index is an unsigned number in the range 1 to either
     NSCds (downstream direction) or NSCus (upstream direction).
     The shaping parameter value is in the range 0 to 127 (units of
     -0.5dB).  The special value 127 indicates that the subcarrier
     is not transmitted."
   REFERENCE  "ITU-T G.997.1, paragraph 7.5.1.21.5 (TSSpsds)
               and paragraph 7.5.1.21.6 (TSSpsus)"
     ::= { adsl2SCStatusEntry 6 }

adsl2SCStatusLinScale  OBJECT-TYPE
   SYNTAX      Unsigned32
   MAX-ACCESS  read-only
   STATUS      current
   DESCRIPTION
     "The scale factor to be applied to the H(f) linear
     representation values for the respective transmission direction.
     This parameter is only available after a loop diagnostic
     procedure."
   REFERENCE  "ITU-T G.997.1, paragraph 7.5.1.18.1 (HLINSCds)
               and paragraph 7.5.1.18.5 (HLINSCus)"
     ::= { adsl2SCStatusEntry 7 }

adsl2SCStatusLinReal  OBJECT-TYPE
   SYNTAX      OCTET STRING  (SIZE(0..1024))
   MAX-ACCESS  read-only
   STATUS      current
   DESCRIPTION
     "An array of up to 512 complex H(f) linear representation
     values in linear scale for the respective transmission
     direction.  It is designed to support up to 512 (downstream)
     sub-carriers.
     The number of utilized values on downstream direction depends
     on NSCds, and on upstream direction it depends on NSCus.  This
     value is referred to here as NSC.
     Each array entry represents the real component [referred to here
     as a(i)] of Hlin(f = i*Df) value for a particular sub-carrier
     index i (0 <= i < NSC).
     Hlin(f) is represented as ((scale/2^15)*((a(i)+j*b(i))/2^15)),
     where scale is Adsl2SubcarrierLinScale and a(i) and b(i)
     [provided by the Adsl2SubcarrierLinImg object] are in the range
     (-2^15+1) to (+2^15-1).
     A special value a(i)=b(i)= -2^15 indicates that no measurement
     could be done for the subcarrier because it is out of the
     passband or that the attenuation is out of range to be
     represented.  This parameter is only available after a loop
     diagnostic procedure.



     Each value in this array is 16 bits wide and is stored in big
     endian format."
   REFERENCE  "ITU-T G.997.1, paragraph 7.5.1.18.2 (HLINpsds)
               and paragraph 7.5.1.18.6 (HLINpsds)"
     ::= { adsl2SCStatusEntry 8 }

adsl2SCStatusLinImg  OBJECT-TYPE
   SYNTAX      OCTET STRING  (SIZE(0..1024))
   MAX-ACCESS  read-only
   STATUS      current
   DESCRIPTION
     "An array of up to 512 complex H(f) linear representation
     values in linear scale for the respective transmission
     direction.  It is designed to support up to 512 (downstream)
     sub-carriers.
     The number of utilized values on downstream direction depends
     on NSCds, and on upstream direction it depends on NSCus.  This
     value is referred to here as NSC.
     Each array entry represents the imaginary component [referred
     to here as b(i)] of Hlin(f = i*Df) value for a particular sub-
     carrier index i (0 <= i < NSC).
     Hlin(f) is represented as ((scale/2^15)*((a(i)+j*b(i))/2^15)),
     where scale is Adsl2SubcarrierLinScale and a(i) [provided by
     the Adsl2SubcarrierLinReal object] and b(i) are in the range
     (-2^15+1) to (+2^15-1).
     A special value a(i)=b(i)= -2^15 indicates that no measurement
     could be done for the subcarrier because it is out of the
     passband or that the attenuation is out of range to be
     represented.  This parameter is only available after a loop
     diagnostic procedure.
     Each value in this array is 16 bits wide and is stored in big
     endian format."
   REFERENCE  "ITU-T G.997.1, paragraph 7.5.1.18.2 (HLINpsds)
               and paragraph 7.5.1.18.6 (HLINpsds)"
     ::= { adsl2SCStatusEntry 9 }

adsl2SCStatusLogMt  OBJECT-TYPE
   SYNTAX      Unsigned32
   MAX-ACCESS  read-only
   STATUS      current
   DESCRIPTION
     "The number of symbols used to measure the H(f) logarithmic
     measurement values for the respective transmission direction.
     This parameter should correspond to the value specified in the
     recommendation (e.g., the number of symbols in 1 second
     time interval for G.992.3).  This parameter corresponds to 1
     second in loop diagnostic procedure and should be updated in
     initialization"



   REFERENCE  "ITU-T G.997.1, paragraph 7.5.1.18.3 (HLOGMTds)
               and paragraph 7.5.1.18.7 (HLOGMTus)"
     ::= { adsl2SCStatusEntry 10 }

adsl2SCStatusLog  OBJECT-TYPE
   SYNTAX      OCTET STRING  (SIZE(0..1024))
   MAX-ACCESS  read-only
   STATUS      current
   DESCRIPTION
     "An array of up to 512 real H(f) logarithmic representation
      values in dB for the respective transmission direction.  It is
      designed to support up to 512 (downstream) sub-carriers.
      The number of utilized values on downstream direction depends
      on NSCds, and on upstream direction it depends on NSCus.  This
      value is referred to here as NSC.
      Each array entry represents the real Hlog(f = i*Df) value for a
      particular sub-carrier index i, (0 <= i < NSC).
      The real Hlog(f) value is represented as (6-m(i)/10), with m(i)
      in the range 0 to 1022.  A special value m=1023 indicates that
      no measurement could be done for the subcarrier because it is
      out of the passband or that the attenuation is out of range to
      be represented.  This parameter is applicable in loop
      diagnostic procedure and initialization.
      Each value in this array is 16 bits wide and is stored
      in big endian format."
   REFERENCE  "ITU-T G.997.1, paragraph 7.5.1.18.4 (HLOGpsds)
               and paragraph 7.5.1.18.8 (HLOGpsus)"
     ::= { adsl2SCStatusEntry 11 }

adsl2SCStatusQlnMt  OBJECT-TYPE
   SYNTAX      Unsigned32
   MAX-ACCESS  read-only
   STATUS      current
   DESCRIPTION
     "The number of symbols used to measure the Quiet Line Noise
      values on the respective transmission direction.  This
      parameter should correspond to the value specified in the
      recommendation (e.g., the number of symbols in 1 second time
      interval for G.992.3).  This parameter corresponds to 1 second
      in loop diagnostic procedure and should be updated in
      initialization "
   REFERENCE  "ITU-T G.997.1, paragraph 7.5.1.19.1 (QLNMTds)
               and paragraph 7.5.1.19.3 (QLNMTus)"
     ::= { adsl2SCStatusEntry 12 }

adsl2SCStatusQln  OBJECT-TYPE
   SYNTAX      OCTET STRING  (SIZE(0..512))
   UNITS       "dBm/Hz"



   MAX-ACCESS  read-only
   STATUS      current
   DESCRIPTION
     "An array of up to 512 real Quiet Line Noise values in dBm/Hz
     for the respective transmission direction.  It is designed for
     up to 512 (downstream) sub-carriers.
     The number of utilized values on downstream direction depends
     on NSCds, and on upstream direction it depends on NSCus.  This
     value is referred to here as NSC.
     Each array entry represents the QLN(f = i*Df) value for a
     particular sub-carrier index i, (0 <= i < NSC).
     The QLN(f) is represented as ( -23-n(i)/2), with n(i) in the
     range 0 to 254.  A special value n(i)=255 indicates that no
     measurement could be done for the subcarrier because it is out
     of the passband or that the noise PSD is out of range to be
     represented.
     This parameter is applicable in loop diagnostic procedure and
     initialization.  Each value in this array is 8 bits wide."
   REFERENCE  "ITU-T G.997.1, paragraph 7.5.1.19.2 (QLNpsds)
               and paragraph 7.5.1.19.4 (QLNpsus)"
     ::= { adsl2SCStatusEntry 13 }

adsl2SCStatusLnAtten  OBJECT-TYPE
   SYNTAX      Unsigned32 (0..1270 | 2147483646 | 2147483647)
   UNITS       "0.1 dB"
   MAX-ACCESS  read-only
   STATUS      current
   DESCRIPTION
      "When referring to the downstream direction, it is the measured
       difference in the total power transmitted by the ATU-C and the
       total power received by the ATU-R over all sub-carriers during
       diagnostics mode.
       When referring to the upstream direction, it is the measured
       difference in the total power transmitted by the ATU-R and the
       total power received by the ATU-C over all sub-carriers during
       diagnostics mode.
       It ranges from 0 to 1270 units of 0.1 dB (physical values are
       0 to 127 dB).
       A special value of 0x7FFFFFFF (2147483647) indicates the line
       attenuation is out of range to be represented.
       A special value of 0x7FFFFFFE (2147483646) indicates the line
       attenuation measurement is unavailable.
       This object reflects the value of the parameter following the
       most recent DELT performed on the associated line.  Once
       the DELT process is over, the parameter no longer changes
       until the row is deleted or a new DELT process is initiated."
   REFERENCE  "ITU-T G.997.1, paragraph 7.5.1.6 (LATNds)
               and paragraph 7.5.1.7 (LATNus)"



   ::= { adsl2SCStatusEntry 14 }

adsl2SCStatusSigAtten  OBJECT-TYPE
   SYNTAX      Unsigned32 (0..1270 | 2147483646 | 2147483647)
   UNITS       "0.1 dB"
   MAX-ACCESS  read-only
   STATUS      current
   DESCRIPTION
      "When referring to the downstream direction, it is the measured
       difference in the total power transmitted by the
       ATU-C and the total power received by the ATU-R over all sub-
       carriers during Showtime after the diagnostics mode.
       When referring to the upstream direction, it is the measured
       difference in the total power transmitted by the
       ATU-R and the total power received by the ATU-C over all sub-
       carriers during Showtime after the diagnostics mode.
       It ranges from 0 to 1270 units of 0.1 dB (physical values
       are 0 to 127 dB).
       A special value of 0x7FFFFFFF (2147483647) indicates the
       signal attenuation is out of range to be represented.
       A special value of 0x7FFFFFFE (2147483646) indicates the
       signal attenuation measurement is unavailable.
       This object reflects the value of the parameter following the
       most recent DELT performed on the associated line.  Once
       the DELT process is over, the parameter no longer changes
       until the row is deleted or a new DELT process is initiated."
   REFERENCE  "ITU-T G.997.1, paragraph 7.5.1.8 (SATNds)
               and paragraph 7.5.1.9 (SATNus)"
   ::= { adsl2SCStatusEntry 15 }

adsl2SCStatusSnrMargin  OBJECT-TYPE
   SYNTAX      Integer32 (-640..630 | 2147483646 | 2147483647)
   UNITS       "0.1 dB"
   MAX-ACCESS  read-only
   STATUS      current
   DESCRIPTION
      "SNR Margin is the maximum increase in dB of the noise power
       received at the ATU (ATU-R on downstream direction and ATU-C
       on upstream direction), such that the BER requirements are met
       for all bearer channels received at the ATU.  It ranges from
       -640 to 630 units of 0.1 dB (physical values are -64 to
       63 dB).
       A special value of 0x7FFFFFFF (2147483647) indicates the
       SNR Margin is out of range to be represented.
       A special value of 0x7FFFFFFE (2147483646) indicates the
       SNR Margin measurement is currently unavailable.
       This object reflects the value of the parameter following the
       most recent DELT performed on the associated line.  Once



       the DELT process is over, the parameter no longer changes
       until the row is deleted or a new DELT process is initiated."
   REFERENCE  "ITU-T G.997.1, paragraph 7.5.1.10 (SNRMds)
               and paragraph 7.5.1.11 (SNRMus)"
   ::= { adsl2SCStatusEntry 16 }

adsl2SCStatusAttainableRate  OBJECT-TYPE
   SYNTAX      Unsigned32
   UNITS       "bits/second"
   MAX-ACCESS  read-only
   STATUS      current
   DESCRIPTION
      "Maximum Attainable Data Rate.  The maximum net data rate
       currently attainable by the ATU-C transmitter and ATU-R
       receiver (when referring to downstream direction) or by the
       ATU-R transmitter and ATU-C receiver (when referring to
       upstream direction).  Value is coded in bits/second.
       This object reflects the value of the parameter following the
       most recent DELT performed on the associated line.  Once
       the DELT process is over, the parameter no longer changes
       until the row is deleted or a new DELT process is initiated."
   REFERENCE  "ITU-T G.997.1, paragraph 7.5.1.12 (ATTNDRds)
               and paragraph 7.5.1.13 (ATTNDRus)"
   ::= { adsl2SCStatusEntry 17 }

adsl2SCStatusActAtp  OBJECT-TYPE
   SYNTAX      Integer32
   UNITS       "0.1 dB"
   MAX-ACCESS  read-only
   STATUS      current
   DESCRIPTION
      "Actual Aggregate Transmit Power from the ATU (ATU-R on
       downstream direction and ATU-C on upstream direction), at the
       instant of measurement.  It ranges from -310 to 310 units of
       0.1 dB (physical values are -31 to 31 dBm).  A value of all
       1's indicates the measurement is out of range to be
       represented.
       This object reflects the value of the parameter following the
       most recent DELT performed on the associated line.  Once
       the DELT process is over, the parameter no longer changes
       until the row is deleted or a new DELT process is initiated."
   REFERENCE  "ITU-T G.997.1, paragraph 7.5.1.16 (ACTATPds)
               and paragraph 7.5.1.17 (ACTATPus)"
   ::= { adsl2SCStatusEntry 18 }

adsl2SCStatusRowStatus  OBJECT-TYPE
   SYNTAX      RowStatus
   MAX-ACCESS  read-create



   STATUS      current
   DESCRIPTION
      "Row Status.  The manager may create and delete rows
       of this table.  Please see the description of
       adsl2SCStatusTable above for more details."
   ::= { adsl2SCStatusEntry 19 }

------------------------------------------------
--        adsl2LineInventoryTable             --
------------------------------------------------
adsl2LineInventoryTable  OBJECT-TYPE
   SYNTAX      SEQUENCE  OF  Adsl2LineInventoryEntry
   MAX-ACCESS  not-accessible
   STATUS      current
   DESCRIPTION
      "The table adsl2LineInventoryTable contains inventory of the
       ADSL2 units."
   ::= { adsl2Inventory 1 }

adsl2LineInventoryEntry  OBJECT-TYPE
   SYNTAX      Adsl2LineInventoryEntry
   MAX-ACCESS  not-accessible
   STATUS      current
   DESCRIPTION
      "The table adsl2LineInventoryTable contains inventory of the
       ADSL2 units.
       The index of this table is an interface index where the
       interface has an ifType of adsl2plus(238)."
   INDEX  { ifIndex, adsl2LInvUnit }
   ::= { adsl2LineInventoryTable 1 }

Adsl2LineInventoryEntry  ::=
   SEQUENCE {
      adsl2LInvUnit                      Adsl2Unit,
      adsl2LInvG994VendorId              OCTET STRING,
      adsl2LInvSystemVendorId            OCTET STRING,
      adsl2LInvVersionNumber             OCTET STRING,
      adsl2LInvSerialNumber              OCTET STRING,
      adsl2LInvSelfTestResult            Unsigned32,
      adsl2LInvTransmissionCapabilities  Adsl2TransmissionModeType
   }

adsl2LInvUnit  OBJECT-TYPE
   SYNTAX      Adsl2Unit
   MAX-ACCESS  not-accessible
   STATUS      current
   DESCRIPTION
      "The termination unit atuc(1) or atur(2)."



   ::= { adsl2LineInventoryEntry 1 }

adsl2LInvG994VendorId  OBJECT-TYPE
   SYNTAX      OCTET STRING  (SIZE(8))
   MAX-ACCESS  read-only
   STATUS      current
   DESCRIPTION
      "The ATU G.994.1 Vendor ID as inserted in the G.994.1 CL/CLR
       message.  It consists of 8 binary octets, including a country
       code followed by a (regionally allocated) provider code, as
       defined in Recommendation T.35."
   REFERENCE    "ITU-T G.997.1, paragraph 7.4"
   ::= { adsl2LineInventoryEntry 2 }

adsl2LInvSystemVendorId  OBJECT-TYPE
   SYNTAX      OCTET STRING  (SIZE(8))
   MAX-ACCESS  read-only
   STATUS      current
   DESCRIPTION
      "The ATU System Vendor ID (identifies the ATU system
       integrator) as inserted in the Overhead Messages (both ATUs
       for G.992.3 and G.992.4) or in the Embedded Operations
       Channel (only ATU-R in G.992.1 and G.992.2).  It consists of
       8 binary octets, with the same format as used for
       Adsl2InvG994VendorId."
   REFERENCE    "ITU-T G.997.1, paragraph 7.4"
   ::= { adsl2LineInventoryEntry 3 }

adsl2LInvVersionNumber  OBJECT-TYPE
   SYNTAX      OCTET STRING  (SIZE(0..16))
   MAX-ACCESS  read-only
   STATUS      current
   DESCRIPTION
      "The ATU version number (vendor-specific information) as
       inserted in the Overhead Messages (both ATUs for G.992.3 and
       G.992.4) or in the Embedded Operations Channel (only ATU-R in
       G.992.1 and G.992.2).  It consists of up to 16 binary octets."
   REFERENCE    "ITU-T G.997.1, paragraph 7.4"
   ::= { adsl2LineInventoryEntry 4 }

adsl2LInvSerialNumber  OBJECT-TYPE
   SYNTAX      OCTET STRING  (SIZE(0..32))
   MAX-ACCESS  read-only
   STATUS      current
   DESCRIPTION
      "The ATU serial number (vendor-specific information) as
       inserted in the Overhead Messages (both ATUs for G.992.3 and
       G.992.4) or in the Embedded Operations Channel (only ATU-R in



       G.992.1 and G.992.2).  It is vendor-specific information.  It
       consists of up to 32 ASCII characters."
   REFERENCE    "ITU-T G.997.1, paragraph 7.4"
   ::= { adsl2LineInventoryEntry 5 }

adsl2LInvSelfTestResult  OBJECT-TYPE
   SYNTAX      Unsigned32
   MAX-ACCESS  read-only
   STATUS      current
   DESCRIPTION
      "The ATU self-test result, coded as a 32-bit value.  The
       most significant octet of the result is '0' if the self-test
       passed, and '1' if the self-test failed.  The interpretation
       of the other octets is vendor discretionary."
   REFERENCE    "ITU-T G.997.1, paragraph 7.4"
   ::= { adsl2LineInventoryEntry 6 }

adsl2LInvTransmissionCapabilities  OBJECT-TYPE
   SYNTAX      Adsl2TransmissionModeType
   MAX-ACCESS  read-only
   STATUS      current
   DESCRIPTION
      "The ATU transmission system capability list of the different
       coding types.  It is coded in a bit-map representation with 1
       or more bits set.  A bit set to '1' means that the ATU
       supports the respective coding.  The value may be derived
       from the handshaking procedures defined in G.994.1.  A set
       of ADSL2 line transmission modes, with one bit per mode."
   REFERENCE    "ITU-T G.997.1, paragraph 7.4"
   ::= { adsl2LineInventoryEntry 7 }


------------------------------------------------
--        adsl2LineConfTemplateTable          --
------------------------------------------------
adsl2LineConfTemplateTable  OBJECT-TYPE
   SYNTAX      SEQUENCE  OF  Adsl2LineConfTemplateEntry
   MAX-ACCESS  not-accessible
   STATUS      current
   DESCRIPTION
      "The table adsl2LineConfTemplateTable contains ADSL2 line
       configuration templates.

       Entries in this table MUST be maintained in a
       persistent manner."
   ::= { adsl2ProfileLine 1 }

adsl2LineConfTemplateEntry  OBJECT-TYPE



   SYNTAX      Adsl2LineConfTemplateEntry
   MAX-ACCESS  not-accessible
   STATUS      current
   DESCRIPTION
      "The table adsl2LineConfTemplateTable contains the ADSL2 line
       configuration template.
       A default template with an index of 'DEFVAL' will
       always exist, and its parameters will be set to vendor-
       specific values, unless otherwise specified in this document."
   INDEX  { adsl2LConfTempTemplateName }
   ::= { adsl2LineConfTemplateTable 1 }

Adsl2LineConfTemplateEntry  ::=
   SEQUENCE {
      adsl2LConfTempTemplateName      SnmpAdminString,
      adsl2LConfTempLineProfile       SnmpAdminString,
      adsl2LConfTempChan1ConfProfile  SnmpAdminString,
      adsl2LConfTempChan1RaRatioDs    Unsigned32,
      adsl2LConfTempChan1RaRatioUs    Unsigned32,
      adsl2LConfTempChan2ConfProfile  SnmpAdminString,
      adsl2LConfTempChan2RaRatioDs    Unsigned32,
      adsl2LConfTempChan2RaRatioUs    Unsigned32,
      adsl2LConfTempChan3ConfProfile  SnmpAdminString,
      adsl2LConfTempChan3RaRatioDs    Unsigned32,
      adsl2LConfTempChan3RaRatioUs    Unsigned32,
      adsl2LConfTempChan4ConfProfile  SnmpAdminString,
      adsl2LConfTempChan4RaRatioDs    Unsigned32,
      adsl2LConfTempChan4RaRatioUs    Unsigned32,
      adsl2LConfTempRowStatus         RowStatus
   }

adsl2LConfTempTemplateName  OBJECT-TYPE
   SYNTAX      SnmpAdminString (SIZE(1..32))
   MAX-ACCESS  not-accessible
   STATUS      current
   DESCRIPTION
      "This object identifies a row in this table."
   REFERENCE    "DSL Forum TR-90, paragraph 5.1.4"
   ::= { adsl2LineConfTemplateEntry 1 }

adsl2LConfTempLineProfile  OBJECT-TYPE
   SYNTAX      SnmpAdminString (SIZE(1..32))
   MAX-ACCESS  read-create
   STATUS      current
   DESCRIPTION
      "The value of this object identifies the row in the ADSL2 Line
       Configuration Profile Table, (adsl2LineConfProfTable),
       which applies for this ADSL2 line."



   REFERENCE    "DSL Forum TR-90, paragraph 5.1.4"
   DEFVAL       { "DEFVAL" }
   ::= { adsl2LineConfTemplateEntry 2 }

adsl2LConfTempChan1ConfProfile  OBJECT-TYPE
   SYNTAX      SnmpAdminString (SIZE(1..32))
   MAX-ACCESS  read-create
   STATUS      current
   DESCRIPTION
      "The value of this object identifies the row in the ADSL2
       Channel Configuration Profile Table,
       (adsl2ChConfProfileTable) that applies to ADSL2 bearer
       channel #1.  The channel profile name specified here must
       match the name of an existing row in the
       adsl2ChConfProfileTable table."
   DEFVAL       { "DEFVAL" }
   ::= { adsl2LineConfTemplateEntry 3 }

adsl2LConfTempChan1RaRatioDs  OBJECT-TYPE
   SYNTAX      Unsigned32(0..100)
   UNITS       "percent"
   MAX-ACCESS  read-create
   STATUS      current
   DESCRIPTION
      "Rate Adaptation Ratio.  The ratio (in %) that should be taken
       into account for the bearer channel #1 when performing rate
       adaptation on Downstream.  The ratio refers to the available
       data rate in excess of the Minimum Data Rate, summed over all
       bearer channels.  Also, the 100 -
       adsl2LConfTempChan1RaRatioDs is the ratio of excess data
       rate to be assigned to all other bearer channels on Downstream
       direction.  The sum of rate adaptation ratios over all bearers
       on the same direction shall be equal to 100%."
   REFERENCE    "ITU-T G.997.1, paragraph 7.3.2.1"
   DEFVAL       { 100 }
   ::= { adsl2LineConfTemplateEntry 4 }

adsl2LConfTempChan1RaRatioUs  OBJECT-TYPE
   SYNTAX      Unsigned32(0..100)
   UNITS       "percent"
   MAX-ACCESS  read-create
   STATUS      current
   DESCRIPTION
      "Rate Adaptation Ratio.  The ratio (in %) that should be taken
       into account for the bearer channel #1 when performing rate
       adaptation on Upstream.  The ratio refers to the available
       data rate in excess of the Minimum Data Rate, summed over all
       bearer channels.  Also, the



       100 - adsl2LConfTempChan1RaRatioUs is the ratio of excess
       data rate to be assigned to all other bearer channels on
       Upstream direction.  The sum of rate adaptation ratios over
       all bearers on the same direction shall be equal to 100%."
   REFERENCE    "ITU-T G.997.1, paragraph 7.3.2.1"
   DEFVAL       { 100 }
   ::= { adsl2LineConfTemplateEntry 5 }

adsl2LConfTempChan2ConfProfile  OBJECT-TYPE
   SYNTAX      SnmpAdminString (SIZE(0..32))
   MAX-ACCESS  read-create
   STATUS      current
   DESCRIPTION
      "The value of this object identifies the row in the ADSL2
       Channel Configuration Profile Table
       (adsl2ChConfProfileTable) that applies to ADSL2 bearer
       channel #2.  If the channel is unused, then the object is set
       to a zero-length string.
       This object may be set to a zero-length string only if
       adsl2LConfTempChan3ConfProfile contains a zero-length
       string."

   DEFVAL       { "" }
   ::= { adsl2LineConfTemplateEntry 6 }

adsl2LConfTempChan2RaRatioDs  OBJECT-TYPE
   SYNTAX      Unsigned32(0..100)
   UNITS       "percent"
   MAX-ACCESS  read-create
   STATUS      current
   DESCRIPTION
      "Rate Adaptation Ratio.  The ratio (in %) that should be taken
       into account for the bearer channel #2 when performing rate
       adaptation on Downstream.  The ratio refers to the available
       data rate in excess of the Minimum Data Rate, summed over all
       bearer channels.  Also, the
       100 - adsl2LConfTempChan2RaRatioDs is the ratio of excess
       data rate to be assigned to all other bearer channels on
       Downstream direction.  The sum of rate adaptation ratios
       over all bearers on the same direction shall be equal to
       100%."
   REFERENCE    "ITU-T G.997.1, paragraph 7.3.2.1"
   DEFVAL       { 0 }
   ::= { adsl2LineConfTemplateEntry 7 }

adsl2LConfTempChan2RaRatioUs  OBJECT-TYPE
   SYNTAX      Unsigned32(0..100)
   UNITS       "percent"



   MAX-ACCESS  read-create
   STATUS      current
   DESCRIPTION
      "Rate Adaptation Ratio.  The ratio (in %) that should be taken
       into account for the bearer channel #2 when performing rate
       adaptation on Upstream.  The ratio refers to the available
       data rate in excess of the Minimum Data Rate, summed over all
       bearer channels.  Also, the
       100 - adsl2LConfTempChan2RaRatioUs is the ratio of excess
       data rate to be assigned to all other bearer channels on
       Upstream direction.  The sum of rate adaptation ratios over
       all bearers on the same direction shall be equal to 100%."
   REFERENCE    "ITU-T G.997.1, paragraph 7.3.2.1"
   DEFVAL       { 0 }
   ::= { adsl2LineConfTemplateEntry 8 }

adsl2LConfTempChan3ConfProfile  OBJECT-TYPE
   SYNTAX      SnmpAdminString (SIZE(0..32))
   MAX-ACCESS  read-create
   STATUS      current
   DESCRIPTION
      "The value of this object identifies the row in the ADSL2
       Channel Configuration Profile Table
       (adsl2ChConfProfileTable) that applies to ADSL2 bearer
       channel #3.  If the channel is unused, then the object is set
       to a zero-length string.
       This object may be set to a zero-length string only if
       adsl2LConfTempChan4ConfProfile contains a zero-length
       string.
       This object may be set to a non-zero-length string only if
       adsl2LConfTempChan2ConfProfile contains a non-zero-length
       string."
   DEFVAL       { "" }
   ::= { adsl2LineConfTemplateEntry 9 }

adsl2LConfTempChan3RaRatioDs  OBJECT-TYPE
   SYNTAX      Unsigned32(0..100)
   UNITS       "percent"
   MAX-ACCESS  read-create
   STATUS      current
   DESCRIPTION
      "Rate Adaptation Ratio.  The ratio (in %) that should be taken
       into account for the bearer channel #3 when performing rate
       adaptation on Downstream.  The ratio refers to the available
       data rate in excess of the Minimum Data Rate, summed over all
       bearer channels.  Also, the 100 -
       adsl2LConfTempChan3RaRatioDs is the ratio of excess data
       rate to be assigned to all other bearer channels on Downstream



       direction.  The sum of rate adaptation ratios over all bearers
       on the same direction shall be equal to 100%."
   REFERENCE    "ITU-T G.997.1, paragraph 7.3.2.1"
   DEFVAL       { 0 }
   ::= { adsl2LineConfTemplateEntry 10 }

adsl2LConfTempChan3RaRatioUs  OBJECT-TYPE
   SYNTAX      Unsigned32(0..100)
   UNITS       "percent"
   MAX-ACCESS  read-create
   STATUS      current
   DESCRIPTION
      "Rate Adaptation Ratio.  The ratio (in %) that should be taken
       into account for the bearer channel #3 when performing rate
       adaptation on Upstream.  The ratio refers to the available
       data rate in excess of the Minimum Data Rate, summed over all
       bearer channels.  Also, the
       100 - adsl2LConfTempChan3RaRatioUs is the ratio of excess
       data rate to be assigned to all other bearer channels on
       Upstream direction.  The sum of rate adaptation ratios over
       all bearers on the same direction shall be equal to 100%."
   REFERENCE    "ITU-T G.997.1, paragraph 7.3.2.1"
   DEFVAL       { 0 }
   ::= { adsl2LineConfTemplateEntry 11 }

adsl2LConfTempChan4ConfProfile  OBJECT-TYPE
   SYNTAX      SnmpAdminString (SIZE(0..32))
   MAX-ACCESS  read-create
   STATUS      current
   DESCRIPTION
      "The value of this object identifies the row in the ADSL2
       Channel Configuration Profile Table
       (adsl2ChConfProfileTable) that applies to ADSL2 bearer
       channel #4.  If the channel is unused, then the object is set
       to a zero-length string.
       This object may be set to a non-zero-length string only if
       adsl2LConfTempChan3ConfProfile contains a non-zero-length
       string."
   DEFVAL       { "" }
   ::= { adsl2LineConfTemplateEntry 12 }

adsl2LConfTempChan4RaRatioDs  OBJECT-TYPE
   SYNTAX      Unsigned32(0..100)
   UNITS       "percent"
   MAX-ACCESS  read-create
   STATUS      current
   DESCRIPTION
      "Rate Adaptation Ratio.  The ratio (in %) that should be taken



       into account for the bearer channel #4 when performing rate
       adaptation on Downstream.  The ratio refers to the available
       data rate in excess of the Minimum Data Rate, summed over all
       bearer channels.  Also, the 100 -
       adsl2LConfTempChan4RaRatioDs is the ratio of
       excess data rate to be assigned to all other bearer channels.
       The sum of rate adaptation ratios over all bearers on the same
       direction shall sum to 100%."
   REFERENCE    "ITU-T G.997.1, paragraph 7.3.2.1"
   DEFVAL       { 0 }
   ::= { adsl2LineConfTemplateEntry 13 }

adsl2LConfTempChan4RaRatioUs  OBJECT-TYPE
   SYNTAX      Unsigned32(0..100)
   UNITS       "percent"
   MAX-ACCESS  read-create
   STATUS      current
   DESCRIPTION
      "Rate Adaptation Ratio.  The ratio (in %) that should be taken
       into account for the bearer channel #4 when performing rate
       adaptation on Upstream.  The ratio refers to the available
       data rate in excess of the Minimum Data Rate, summed over
       all bearer channels.  Also, the 100 -
       adsl2LConfTempChan4RaRatioUs is the
       ratio of excess data rate to be assigned to all other bearer
       channels.  The sum of rate adaptation ratios over all bearers
       on the same direction shall sum to 100%."
   REFERENCE    "ITU-T G.997.1, paragraph 7.3.2.1"
   DEFVAL       { 0 }
   ::= { adsl2LineConfTemplateEntry 14 }

adsl2LConfTempRowStatus  OBJECT-TYPE
   SYNTAX      RowStatus
   MAX-ACCESS  read-create
   STATUS      current
   DESCRIPTION
      "This object is used to create a new row or to modify or
      delete an existing row in this table.

      A template is activated by setting this object to 'active'.
      When 'active' is set, the system will validate the template.

      Before a template can be deleted or taken out of service
      (by setting this object to 'destroy' or 'notInService'),
      it must first be unreferenced from all associated
      lines."
   ::= { adsl2LineConfTemplateEntry 15 }




------------------------------------------
--        adsl2LineConfProfTable        --
------------------------------------------
adsl2LineConfProfTable  OBJECT-TYPE
   SYNTAX      SEQUENCE  OF  Adsl2LineConfProfEntry
   MAX-ACCESS  not-accessible
   STATUS      current
   DESCRIPTION
      "The table adsl2LineConfProfTable contains ADSL2 line profile
       configuration.

       Entries in this table MUST be maintained in a
       persistent manner."
   ::= { adsl2ProfileLine 2 }

adsl2LineConfProfEntry  OBJECT-TYPE
   SYNTAX      Adsl2LineConfProfEntry
   MAX-ACCESS  not-accessible
   STATUS      current
   DESCRIPTION
      "The table adsl2LineConfProfTable contains ADSL2 line profile
       configuration.

       A default profile with an index of 'DEFVAL' will
       always exist, and its parameters will be set to vendor-
       specific values, unless otherwise specified in this document."
   INDEX  { adsl2LConfProfProfileName }
   ::= { adsl2LineConfProfTable 1 }

Adsl2LineConfProfEntry  ::=
   SEQUENCE {
      adsl2LConfProfProfileName          SnmpAdminString,
      adsl2LConfProfScMaskDs             Adsl2ScMaskDs,
      adsl2LConfProfScMaskUs             Adsl2ScMaskUs,
      adsl2LConfProfRfiBandsDs           Adsl2RfiDs,
      adsl2LConfProfRaModeDs             Adsl2RaMode,
      adsl2LConfProfRaModeUs             Adsl2RaMode,
      adsl2LConfProfRaUsNrmDs            Unsigned32,
      adsl2LConfProfRaUsNrmUs            Unsigned32,
      adsl2LConfProfRaUsTimeDs           Unsigned32,
      adsl2LConfProfRaUsTimeUs           Unsigned32,
      adsl2LConfProfRaDsNrmsDs           Unsigned32,
      adsl2LConfProfRaDsNrmsUs           Unsigned32,
      adsl2LConfProfRaDsTimeDs           Unsigned32,
      adsl2LConfProfRaDsTimeUs           Unsigned32,
      adsl2LConfProfTargetSnrmDs         Unsigned32,
      adsl2LConfProfTargetSnrmUs         Unsigned32,
      adsl2LConfProfMaxSnrmDs            Unsigned32,



      adsl2LConfProfMaxSnrmUs            Unsigned32,
      adsl2LConfProfMinSnrmDs            Unsigned32,
      adsl2LConfProfMinSnrmUs            Unsigned32,
      adsl2LConfProfMsgMinUs             Unsigned32,
      adsl2LConfProfMsgMinDs             Unsigned32,
      adsl2LConfProfAtuTransSysEna       Adsl2TransmissionModeType,
      adsl2LConfProfPmMode               Adsl2LConfProfPmMode,
      adsl2LConfProfL0Time               Unsigned32,
      adsl2LConfProfL2Time               Unsigned32,
      adsl2LConfProfL2Atpr               Unsigned32,
      adsl2LConfProfL2Atprt              Unsigned32,
      adsl2LConfProfRowStatus            RowStatus
   }

adsl2LConfProfProfileName  OBJECT-TYPE
   SYNTAX      SnmpAdminString (SIZE(1..32))
   MAX-ACCESS  not-accessible
   STATUS      current
   DESCRIPTION
      "This object identifies a row in this table."
     ::= { adsl2LineConfProfEntry 1 }

adsl2LConfProfScMaskDs  OBJECT-TYPE
   SYNTAX      Adsl2ScMaskDs
   MAX-ACCESS  read-create
   STATUS      current
   DESCRIPTION
      "Sub-carriers mask.  A bitmap of 512 bits that allows masking
       up to 512 downstream sub-carriers, depending on NSCds.  If bit
       i (0 <= i < NSCds) is set to '1', the respective
       downstream sub-carrier i is masked, and if set to '0', the
       respective sub-carrier is unmasked.  Note that there should
       always be unmasked sub-carriers (i.e., the object cannot be
       all 1's).  Also note that if NSCds < 512, all bits
       i (NSCds < i <= 512) should be set to '1'."
   REFERENCE    "ITU-T G.997.1, paragraph 7.3.1.2.6"
   ::= { adsl2LineConfProfEntry 2 }

adsl2LConfProfScMaskUs  OBJECT-TYPE
   SYNTAX      Adsl2ScMaskUs
   MAX-ACCESS  read-create
   STATUS      current
   DESCRIPTION
      "Sub-carriers mask.  A bitmap of 64 bits that allows masking
       up to 64 downstream sub-carriers, depending on NSCds.  If
       bit i (0 <= i < NSCus) is set to '1', the respective
       upstream sub-carrier i is masked, and if set to '0', the
       respective sub-carrier is unmasked.  Note that there



       should always be unmasked sub-carriers (i.e., the object
       cannot be all 1's).  Also note that if NSCus <
       64, all bits i (NSCus < i <= 64) should be set to '1'."
   REFERENCE    "ITU-T G.997.1, paragraph 7.3.1.2.7"
   ::= { adsl2LineConfProfEntry 3 }

adsl2LConfProfRfiBandsDs  OBJECT-TYPE
   SYNTAX      Adsl2RfiDs
   MAX-ACCESS  read-create
   STATUS      current
   DESCRIPTION
       "The subset of downstream PSD mask breakpoints that shall be
       used to notch an RFI band.
       The specific interpolation around these points is defined in
       G.992.5.  It is a bitmap of 512 bits that allows referring to
       up to 512 downstream sub-carriers, depending on NSCds.  If bit
       i (0 <= i < NSCds) is set to '1', the respective downstream
       sub-carrier i is part of a notch filter, and if set to '0',
       the respective sub-carrier is not part of a notch filter.
       This information complements the specification provided by
       adsl2LConfProfPsdMaskDs.
       Note that if NSCds < 512, all bits i (NSCds<i<512)
       should be set to '0'."
   REFERENCE    "ITU-T G.997.1, paragraph 7.3.1.2.9"
   ::= { adsl2LineConfProfEntry 4 }

adsl2LConfProfRaModeDs  OBJECT-TYPE
   SYNTAX      Adsl2RaMode
   MAX-ACCESS  read-create
   STATUS      current
   DESCRIPTION
      "The mode of operation of a rate-adaptive ATU-C in the transmit
       direction.  The parameter can take three values:
          manual(1),
          raInit(2), or
          dynamicRa(3)."
   REFERENCE    "ITU-T G.997.1, paragraph 7.3.1.4.1"
   DEFVAL       { manual }
   ::= { adsl2LineConfProfEntry 5 }

adsl2LConfProfRaModeUs  OBJECT-TYPE
   SYNTAX      Adsl2RaMode
   MAX-ACCESS  read-create
   STATUS      current
   DESCRIPTION
      "The mode of operation of a rate-adaptive ATU-R in the transmit
       direction.  The parameter can take three values:
          manual(1),



          raInit(2), or
          dynamicRa(3)."
   REFERENCE    "ITU-T G.997.1, paragraph 7.3.1.4.2"
   DEFVAL       { manual }
   ::= { adsl2LineConfProfEntry 6 }

adsl2LConfProfRaUsNrmDs  OBJECT-TYPE
   SYNTAX      Unsigned32(0..310)
   UNITS       "0.1 dB"
   MAX-ACCESS  read-create
   STATUS      current
   DESCRIPTION
      "The Downstream Up-Shift Noise Margin value, to be used when
       adsl2LConfProfRaModeDs is set to dynamicRa.  If the downstream
       noise margin is above this value and stays above it for
       more than the time specified by the adsl2LConfProfRaUsTimeDs,
       the ATU-R shall attempt to increase the downstream net data
       rate.  The Downstream Up-Shift Noise Margin ranges from 0 to
       310 units of 0.1 dB (physical values are 0 to 31 dB)."
   REFERENCE    "ITU-T G.997.1, paragraph 7.3.1.4.3"
   DEFVAL       { 10 }
   ::= { adsl2LineConfProfEntry 7 }

adsl2LConfProfRaUsNrmUs  OBJECT-TYPE
   SYNTAX      Unsigned32(0..310)
   UNITS       "0.1 dB"
   MAX-ACCESS  read-create
   STATUS      current
   DESCRIPTION
      "The Upstream Up-Shift Noise Margin value, to be used when
       adsl2LConfProfRaModeUs is set to dynamicRa.  If the upstream
       noise margin is above this value and stays above it for more
       than the time specified by the adsl2LConfProfRaUsTimeUs, the
       ATU-C shall attempt to increase the upstream net data rate.
       The Upstream Up-Shift Noise Margin ranges from 0 to 310 units
       of 0.1 dB (physical values are 0 to 31 dB)."
   REFERENCE    "ITU-T G.997.1, paragraph 7.3.1.4.4"
   DEFVAL       { 10 }
   ::= { adsl2LineConfProfEntry 8 }

adsl2LConfProfRaUsTimeDs  OBJECT-TYPE
   SYNTAX      Unsigned32(0..16383)
   UNITS       "seconds"
   MAX-ACCESS  read-create
   STATUS      current
   DESCRIPTION
      "The Downstream Up-Shift Time Interval, to be used when
       adsl2LConfProfRaModeDs is set to dynamicRa.  The interval of



       time that the downstream noise margin should stay above the
       Downstream Up-Shift Noise Margin before the ATU-R shall
       attempt to increase the downstream net data rate.  The time
       interval ranges from 0 to 16383 seconds."
   REFERENCE    "ITU-T G.997.1, paragraph 7.3.1.4.5"
   DEFVAL       { 3600 }
   ::= { adsl2LineConfProfEntry 9 }

adsl2LConfProfRaUsTimeUs  OBJECT-TYPE
   SYNTAX      Unsigned32(0..16383)
   UNITS       "seconds"
   MAX-ACCESS  read-create
   STATUS      current
   DESCRIPTION
      "The Upstream Up-Shift Time Interval, to be used when
       adsl2LConfProfRaModeUs is set to dynamicRa.  The interval of
       time the upstream noise margin should stay above the
       Upstream Up-Shift Noise Margin before the ATU-C shall
       attempt to increase the upstream net data rate.  The time
       interval ranges from 0 to 16383 seconds."
   REFERENCE    "ITU-T G.997.1, paragraph 7.3.1.4.6"
   DEFVAL       { 3600 }
   ::= { adsl2LineConfProfEntry 10 }

adsl2LConfProfRaDsNrmsDs  OBJECT-TYPE
   SYNTAX      Unsigned32(0..310)
   UNITS       "0.1 dB"
   MAX-ACCESS  read-create
   STATUS      current
   DESCRIPTION
      "The Downstream Down-Shift Noise Margin value, to be used when
       adsl2LConfProfRaModeDs is set to dynamicRa.  If the downstream
       noise margin is below this value and stays below that for more
       than the time specified by the adsl2LConfProfRaDsTimeDs, the
       ATU-R shall attempt to decrease the downstream net data rate.
       The Downstream Down-Shift Noise Margin ranges from 0 to 310
       units of 0.1 dB (physical values are 0 to 31 dB)."
   REFERENCE    "ITU-T G.997.1, paragraph 7.3.1.4.7"
   DEFVAL       { 10 }
   ::= { adsl2LineConfProfEntry 11 }

adsl2LConfProfRaDsNrmsUs  OBJECT-TYPE
   SYNTAX      Unsigned32(0..310)
   UNITS       "0.1 dB"
   MAX-ACCESS  read-create
   STATUS      current
   DESCRIPTION
      "The Upstream Down-Shift Noise Margin value, to be used when



       adsl2LConfProfRaModeUs is set to dynamicRa.  If the upstream
       noise margin is below this value and stays below that for more
       than the time specified by the adsl2LConfProfRaDsTimeUs, the
       ATU-C shall attempt to decrease the upstream net data rate.
       The Upstream Down-Shift Noise Margin ranges from 0 to 310
       units of 0.1 dB (physical values are 0 to 31 dB)."
   REFERENCE    "ITU-T G.997.1, paragraph 7.3.1.4.8"
   DEFVAL       { 10 }
   ::= { adsl2LineConfProfEntry 12 }

adsl2LConfProfRaDsTimeDs  OBJECT-TYPE
   SYNTAX      Unsigned32(0..16383)
   UNITS       "seconds"
   MAX-ACCESS  read-create
   STATUS      current
   DESCRIPTION
      "The Downstream Down-Shift Time Interval, to be used when
       adsl2LConfProfRaModeDs is set to dynamicRa.  The interval of
       time the downstream noise margin should stay below the
       Downstream Down-Shift Noise Margin before the ATU-R shall
       attempt to decrease the downstream net data rate.  The time
       interval ranges from 0 to 16383 seconds."
   REFERENCE    "ITU-T G.997.1, paragraph 7.3.1.4.9"
   DEFVAL       { 3600 }
   ::= { adsl2LineConfProfEntry 13 }

adsl2LConfProfRaDsTimeUs  OBJECT-TYPE
   SYNTAX      Unsigned32(0..16383)
   UNITS       "seconds"
   MAX-ACCESS  read-create
   STATUS      current
   DESCRIPTION
      "The Upstream Down-Shift Time Interval, to be used when
       adsl2LConfProfRaModeUs is set to dynamicRa.  The interval of
       time the upstream noise margin should stay below the Upstream
       Down-Shift Noise Margin before the ATU-C shall attempt to
       decrease the upstream net data rate.  The time interval ranges
       from 0 to 16383 seconds."
   REFERENCE    "ITU-T G.997.1, paragraph 7.3.1.4.10"
   DEFVAL       { 3600 }
   ::= { adsl2LineConfProfEntry 14 }

adsl2LConfProfTargetSnrmDs  OBJECT-TYPE
   SYNTAX      Unsigned32(0..310)
   UNITS       "0.1 dB"
   MAX-ACCESS  read-create
   STATUS      current
   DESCRIPTION



      "The minimum Noise Margin the ATU-R receiver shall achieve,
       relative to the BER requirement for each of the downstream
       bearer channels, to successfully complete initialization.
       The target noise margin ranges from 0 to 310 units of 0.1 dB
       (physical values are 0 to 31 dB)."
   REFERENCE    "ITU-T G.997.1, paragraph 7.3.1.3.1"
   DEFVAL       { 60 }
   ::= { adsl2LineConfProfEntry 15 }

adsl2LConfProfTargetSnrmUs  OBJECT-TYPE
   SYNTAX      Unsigned32(0..310)
   UNITS       "0.1 dB"
   MAX-ACCESS  read-create
   STATUS      current
   DESCRIPTION
      "The minimum Noise Margin the ATU-C receiver shall achieve,
       relative to the BER requirement for each of the upstream
       bearer channels, to successfully complete initialization.
       The target noise margin ranges from 0 to 310 units of 0.1 dB
       (physical values are 0 to 31 dB)."
   REFERENCE    "ITU-T G.997.1, paragraph 7.3.1.3.2"
   DEFVAL       { 60 }
   ::= { adsl2LineConfProfEntry 16 }

adsl2LConfProfMaxSnrmDs  OBJECT-TYPE
   SYNTAX      Unsigned32 (0..310 | 2147483647)
   UNITS       "0.1 dB"
   MAX-ACCESS  read-create
   STATUS      current
   DESCRIPTION
      "The maximum Noise Margin the ATU-R receiver shall try to
       sustain.  If the Noise Margin is above this level, the ATU-R
       shall request that the ATU-C reduce the ATU-C transmit power
       to get a noise margin below this limit (if this functionality
       is supported).  The maximum noise margin ranges from 0 to 310
       units of 0.1 dB (physical values are 0 to 31 dB).  A value of
       0x7FFFFFFF (2147483647) means that there is no maximum."
   REFERENCE    "ITU-T G.997.1, paragraph 7.3.1.3.3"
   DEFVAL       { 310 }
   ::= { adsl2LineConfProfEntry 17 }

adsl2LConfProfMaxSnrmUs  OBJECT-TYPE
   SYNTAX      Unsigned32 (0..310 | 2147483647)
   UNITS       "0.1 dB"
   MAX-ACCESS  read-create
   STATUS      current
   DESCRIPTION
      "The maximum Noise Margin the ATU-C receiver shall try to



       sustain.  If the Noise Margin is above this level, the ATU-C
       shall request that the ATU-R reduce the ATU-R transmit power
       to get a noise margin below this limit (if this functionality
       is supported).  The maximum noise margin ranges from 0 to 310
       units of 0.1 dB (physical values are 0 to 31 dB).  A value of
       0x7FFFFFFF (2147483647) means that there is no maximum."
   REFERENCE    "ITU-T G.997.1, paragraph 7.3.1.3.4"
   DEFVAL       { 310 }
   ::= { adsl2LineConfProfEntry 18 }

adsl2LConfProfMinSnrmDs  OBJECT-TYPE
   SYNTAX      Unsigned32(0..310)
   UNITS       "0.1 dB"
   MAX-ACCESS  read-create
   STATUS      current
   DESCRIPTION
      "The minimum Noise Margin the ATU-R receiver shall tolerate.
       If the noise margin falls below this level, the ATU-R shall
       request that the ATU-C increase the ATU-C transmit power.
       If an increase to ATU-C transmit power is not possible, a
       loss-of-margin (LOM) defect occurs, the ATU-R shall fail and
       attempt to reinitialize, and the NMS shall be notified.  The
       minimum noise margin ranges from 0 to 310 units of
       0.1 dB (physical values are 0 to 31 dB).  A value of 0 means
       that there is no minimum."
   REFERENCE    "ITU-T G.997.1, paragraph 7.3.1.3.5"
   DEFVAL       { 10 }
   ::= { adsl2LineConfProfEntry 19 }

adsl2LConfProfMinSnrmUs  OBJECT-TYPE
   SYNTAX      Unsigned32(0..310)
   UNITS       "0.1 dB"
   MAX-ACCESS  read-create
   STATUS      current
   DESCRIPTION
      "The minimum Noise Margin the ATU-C receiver shall tolerate.
       If the noise margin falls below this level, the ATU-C shall
       request that the ATU-R increase the ATU-R transmit power.
       If an increase of ATU-R transmit power is not possible, a
       loss-of-margin (LOM) defect occurs, the ATU-C shall fail and
       attempt to reinitialize, and the NMS shall be notified.  The
       minimum noise margin ranges from 0 to 310 units of
       0.1 dB (physical values are 0 to 31 dB).  A value of 0 means
       that there is no minimum."
   REFERENCE    "ITU-T G.997.1, paragraph 7.3.1.3.6"
   DEFVAL       { 10 }
   ::= { adsl2LineConfProfEntry 20 }




adsl2LConfProfMsgMinUs  OBJECT-TYPE
   SYNTAX      Unsigned32(4000..63000)
   UNITS       "bits/second"
   MAX-ACCESS  read-create
   STATUS      current
   DESCRIPTION
      "Minimum Overhead Rate Upstream.  Defines the minimum rate of
       the message-based overhead that shall be maintained by the ATU
       in upstream direction.  Expressed in bits per second and
       ranges from 4000 to 63000 bps."
   REFERENCE    "ITU-T G.997.1, paragraph 7.3.1.5.1"
   DEFVAL       { 4000 }
  ::= { adsl2LineConfProfEntry 21 }

adsl2LConfProfMsgMinDs  OBJECT-TYPE
   SYNTAX      Unsigned32(4000..63000)
   UNITS       "bits/second"
   MAX-ACCESS  read-create
   STATUS      current
   DESCRIPTION
      "Minimum Overhead Rate Downstream.  Defines the minimum rate of
       the message-based overhead that shall be maintained by the ATU
       in downstream direction.  Expressed in bits per second and
       ranges from 4000 to 63000 bps."
   REFERENCE    "ITU-T G.997.1, paragraph 7.3.1.5.2"
   DEFVAL       { 4000 }
   ::= { adsl2LineConfProfEntry 22 }

adsl2LConfProfAtuTransSysEna  OBJECT-TYPE
   SYNTAX      Adsl2TransmissionModeType
   MAX-ACCESS  read-create
   STATUS      current
   DESCRIPTION
      "ATU Transmission System Enabling (ATSE).  A list of the
       different coding types enabled in this profile.  It is coded
       in a bit-map representation with 1 or more bits set.  A bit
       set to  '1' means that the ATUs may apply the respective
       coding for the ADSL line.  A bit set to '0' means that
       the ATUs cannot apply the respective coding for the ADSL
       line.  All 'reserved' bits should be set to '0'."
   REFERENCE    "ITU-T G.997.1, paragraph 7.3.1.1.1"
   ::= { adsl2LineConfProfEntry 23 }

adsl2LConfProfPmMode  OBJECT-TYPE
   SYNTAX      Adsl2LConfProfPmMode
   MAX-ACCESS  read-create
   STATUS      current
   DESCRIPTION



      "Power management state Enabling.  Defines the power states the
       ATU-C or ATU-R may autonomously transition to on this line.
       The various bit positions are: allowTransitionsToIdle(0) and
       allowTransitionsToLowPower(1).  A bit with a '1' value means
       that the ATU is allowed to transit into the respective state,
       and a '0' value means that the ATU is not allowed
       to transit into the respective state."
   REFERENCE    "ITU-T G.997.1, paragraph 7.3.1.1.4"
   DEFVAL  { { allowTransitionsToIdle, allowTransitionsToLowPower } }
   ::= { adsl2LineConfProfEntry 24 }

adsl2LConfProfL0Time  OBJECT-TYPE
   SYNTAX      Unsigned32 (0..255)
   UNITS       "seconds"
   MAX-ACCESS  read-create
   STATUS      current
   DESCRIPTION
      "This minimum time (in seconds) between an Exit from the L2
       state and the next Entry into the L2 state.  It ranges from 0
       to 255 seconds."
   REFERENCE    "ITU-T G.997.1, paragraph 7.3.1.1.5"
   DEFVAL       { 255 }
   ::= { adsl2LineConfProfEntry 25 }

adsl2LConfProfL2Time  OBJECT-TYPE
   SYNTAX      Unsigned32 (0..255)
   UNITS       "seconds"
   MAX-ACCESS  read-create
   STATUS      current
   DESCRIPTION
      "This minimum time (in seconds) between an Entry into the
      L2 state and the first Power Trim in the L2 state and between
      two consecutive Power Trims in the L2 State.
      It ranges from 0 to 255 seconds."
   REFERENCE    "ITU-T G.997.1, paragraph 7.3.1.1.6"
   DEFVAL       { 255 }
   ::= { adsl2LineConfProfEntry 26 }

adsl2LConfProfL2Atpr  OBJECT-TYPE
   SYNTAX      Unsigned32 (0..31)
   UNITS       "dB"
   MAX-ACCESS  read-create
   STATUS      current
   DESCRIPTION
      "The maximum aggregate transmit power reduction (in dB) that
       can be performed at transition of L0 to L2 state or through a
       single Power Trim in the L2 state.
       It ranges from 0 dB to 31 dB."



   REFERENCE    "ITU-T G.997.1 (amendment 1), 7.3.1.1.7"
   DEFVAL       { 10 }
   ::= { adsl2LineConfProfEntry 27 }

adsl2LConfProfL2Atprt  OBJECT-TYPE
   SYNTAX      Unsigned32 (0..31)
   UNITS       "dB"
   MAX-ACCESS  read-create
   STATUS      current
   DESCRIPTION
      "The total maximum aggregate transmit power reduction
      (in dB) that can be performed in an L2 state.  This is the
      sum of all reductions of L2 Request (i.e., at transition of
      L0 to L2 state) and Power Trims."
   REFERENCE    "ITU-T G.997.1 (amendment 1), 7.3.1.1.9"
   DEFVAL       { 31 }
   ::= { adsl2LineConfProfEntry 28 }

adsl2LConfProfRowStatus  OBJECT-TYPE
   SYNTAX      RowStatus
   MAX-ACCESS  read-create
   STATUS      current
   DESCRIPTION
      "This object is used to create a new row or to modify or
      delete an existing row in this table.

      A profile is activated by setting this object to 'active'.
      When 'active' is set, the system will validate the profile.

      Before a profile can be deleted or taken out of service
      (by setting this object to 'destroy' or 'notInService'),
      it must first be unreferenced from all associated
      templates."
   ::= { adsl2LineConfProfEntry 29 }


------------------------------------------
--    adsl2LineConfProfModeSpecTable    --
------------------------------------------
adsl2LineConfProfModeSpecTable  OBJECT-TYPE
   SYNTAX      SEQUENCE  OF  Adsl2LineConfProfModeSpecEntry
   MAX-ACCESS  not-accessible
   STATUS      current
   DESCRIPTION
      "The table adsl2LineConfProfModeSpecTable extends the
       ADSL2 line configuration profile by ADSL Mode Specific
       parameters.
       A row in this table that has an index of



       adsl2LConfProfAdslMode == defMode(1) is called a
       'mandatory' row.
       A row in this table that has an index such that
       adsl2LConfProfAdslMode is not equal to defMode(1)
       is called an 'optional' row.
       When a row in the adsl2LineConfProfTable table
       (the parent row) is created, the SNMP agent will
       automatically create a 'mandatory' row in this table.
       When the parent row is deleted, the SNMP agent will
       automatically delete all associated rows in this table.
       Any attempt to delete the 'mandatory' row using the
       adsl2LConfProfModeSpecRowStatus attribute will be
       rejected by the SNMP agent.
       The manager MAY create an 'optional' row in this table
       using the adsl2LConfProfModeSpecRowStatus attribute if
       the parent row exists.
       The manager MAY delete an 'optional' row in this table
       using the adsl2LConfProfModeSpecRowStatus attribute at
       any time.
       If the actual transmission mode of a DSL line does not
       match one of the 'optional' rows in this table, then
       the line will use the PSD configuration from the
       'mandatory' row.

       Entries in this table MUST be maintained in a
       persistent manner."
   ::= { adsl2ProfileLine 3 }

adsl2LineConfProfModeSpecEntry  OBJECT-TYPE
   SYNTAX      Adsl2LineConfProfModeSpecEntry
   MAX-ACCESS  not-accessible
   STATUS      current
   DESCRIPTION
      "The table adsl2LineConfProfModeSpecTable extends the
       ADSL2 line configuration profile by ADSL Mode Specific
       parameters."
   INDEX  { adsl2LConfProfProfileName, adsl2LConfProfAdslMode }
   ::= { adsl2LineConfProfModeSpecTable 1 }

Adsl2LineConfProfModeSpecEntry  ::=
   SEQUENCE {
      adsl2LConfProfAdslMode             Adsl2OperationModes,
      adsl2LConfProfMaxNomPsdDs          Integer32,
      adsl2LConfProfMaxNomPsdUs          Integer32,
      adsl2LConfProfMaxNomAtpDs          Unsigned32,
      adsl2LConfProfMaxNomAtpUs          Unsigned32,
      adsl2LConfProfMaxAggRxPwrUs        Integer32,
      adsl2LConfProfPsdMaskDs            Adsl2PsdMaskDs,



      adsl2LConfProfPsdMaskUs            Adsl2PsdMaskUs,
      adsl2LConfProfPsdMaskSelectUs      Unsigned32,
      adsl2LConfProfModeSpecRowStatus    RowStatus
   }

adsl2LConfProfAdslMode    OBJECT-TYPE
   SYNTAX      Adsl2OperationModes
   MAX-ACCESS  not-accessible
   STATUS      current
   DESCRIPTION
      "The ADSL Mode is a way of categorizing the various ADSL
       transmission modes into groups; each group (ADSL Mode) shares
       the same PSD configuration.
       There should be multiple entries in this table for a given
       line profile in case multiple bits are set in
       adsl2LConfProfAtuTransSysEna for that profile."
   REFERENCE    "DSL Forum TR-90, paragraph 5.1.8"
   ::= { adsl2LineConfProfModeSpecEntry 1 }

adsl2LConfProfMaxNomPsdDs  OBJECT-TYPE
   SYNTAX      Integer32(-600..-300)
   UNITS       "0.1 dBm/Hz"
   MAX-ACCESS  read-create
   STATUS      current
   DESCRIPTION
      "The maximum nominal transmit PSD in the downstream
       direction during initialization and Showtime.  It ranges from
       -600 to -300 units of 0.1 dBm/Hz (physical values are -60 to
       -30 dBm/Hz)."
   REFERENCE    "ITU-T G.997.1, paragraph 7.3.1.2"
   DEFVAL       { -300 }
  ::= { adsl2LineConfProfModeSpecEntry 2 }

adsl2LConfProfMaxNomPsdUs  OBJECT-TYPE
   SYNTAX      Integer32(-600..-300)
   UNITS       "0.1 dBm/Hz"
   MAX-ACCESS  read-create
   STATUS      current
   DESCRIPTION
      "The maximum nominal transmit PSD in the upstream direction
       during initialization and Showtime.  It ranges from -600 to
       -300 units of 0.1 dBm/Hz (physical values are -60 to
       -30 dBm/Hz)."
   REFERENCE    "ITU-T G.997.1, paragraph 7.3.1.2"
   DEFVAL       { -300 }
   ::= { adsl2LineConfProfModeSpecEntry 3 }

adsl2LConfProfMaxNomAtpDs  OBJECT-TYPE



   SYNTAX      Unsigned32 (0..255)
   UNITS       "0.1 dBm"
   MAX-ACCESS  read-create
   STATUS      current
   DESCRIPTION
      "The maximum nominal aggregate transmit power in the
       downstream direction during initialization and Showtime.  It
       ranges from 0 to 255 units of 0.1 dBm (physical values are 0
       to 25.5 dBm)."
   REFERENCE    "ITU-T G.997.1, paragraph 7.3.1.2"
   DEFVAL       { 255 }
   ::= { adsl2LineConfProfModeSpecEntry 4 }

adsl2LConfProfMaxNomAtpUs  OBJECT-TYPE
   SYNTAX      Unsigned32 (0..255)
   UNITS       "0.1 dBm"
   MAX-ACCESS  read-create
   STATUS      current
   DESCRIPTION
      "The maximum nominal aggregate transmit power in the upstream
       direction during initialization and Showtime.  It ranges from
       0 to 255 units of 0.1 dBm (physical values are 0 to 25.5
       dBm)."
   REFERENCE    "ITU-T G.997.1, paragraph 7.3.1.2"
   DEFVAL       { 255 }
   ::= { adsl2LineConfProfModeSpecEntry 5 }

adsl2LConfProfMaxAggRxPwrUs  OBJECT-TYPE
   SYNTAX      Integer32(-255..255 | 2147483647)
   UNITS       "0.1 dBm"
   MAX-ACCESS  read-create
   STATUS      current
   DESCRIPTION
      "The maximum upstream aggregate receive power over the relevant
       set of sub-carriers.  The ATU-C should verify that the
       upstream power cutback is such that this maximum aggregate
       receive power value is honored.  It ranges from -255 to 255
       units of 0.1 dBm (physical values are -25.5 to 25.5 dBm).
       A value of 0x7FFFFFFF (2147483647) means that there is no
       limit."
   REFERENCE    "ITU-T G.997.1, paragraph 7.3.1.2"
   DEFVAL       { 255 }
   ::= { adsl2LineConfProfModeSpecEntry 6 }

adsl2LConfProfPsdMaskDs   OBJECT-TYPE
   SYNTAX      Adsl2PsdMaskDs
   MAX-ACCESS  read-create
   STATUS      current



   DESCRIPTION
     "The downstream PSD mask applicable at the U-C2 reference
      point.
     This parameter is used only for G.992.5, and it may impose PSD
     restrictions (breakpoints) in addition to the Limit PSD mask
     defined in G.992.5.
     This is a string of 32 pairs of values in the following
     structure:
     Octets 0+1 - Index of 1st sub-carrier used in the context
                  of a first breakpoint.
     Octet 2    - The PSD reduction for the sub-carrier indicated in
                  octets 0 and 1.
     Octets 3-5 - Same, for a 2nd breakpoint.
     Octets 6-8 - Same, for a 3rd breakpoint.
     This architecture continues until octets 94-95, which are
     associated with a 32nd breakpoint.
     Each subcarrier index is an unsigned number in the range 1 to
     NSCds.  Each PSD reduction value is in the range 0 (0dBm/Hz) to
     255 (-127.5dBm/Hz) with steps of 0.5dBm/Hz.  Valid values are
     in the range 0 to 190 (0 to -95dBm/Hz).
     When the number of breakpoints is less than 32, all remaining
     octets are set to the value 0.  Note that the content of this
     object should be correlated with the sub-carriers mask and with
     the RFI setup."
   REFERENCE    "ITU-T G.997.1, paragraph 7.3.1.2"
     ::= { adsl2LineConfProfModeSpecEntry 7 }

adsl2LConfProfPsdMaskUs   OBJECT-TYPE
   SYNTAX      Adsl2PsdMaskUs
   MAX-ACCESS  read-create
   STATUS      current
   DESCRIPTION
     "The upstream PSD mask applicable at the U-R2 reference
      point.
     This parameter is used only for G.992.5, and it may impose PSD
     restrictions (breakpoints) in addition to the Limit PSD mask
     defined in G.992.5.
     This is a string of 4 pairs of values in the following
     structure:
     Octets 0+1 - Index of 1st sub-carrier used in the context
                  of a first breakpoint.
     Octet 2    - The PSD reduction for the sub-carrier indicated in
                  octets 0 and 1.
     Octets 3-5 - Same, for a 2nd breakpoint.
     Octets 6-8 - Same, for a 3rd breakpoint.
     This architecture continues until octets 9-11, which are
     associated with a 4th breakpoint.
     Each subcarrier index is an unsigned number in the range 1 to



     NSCus.  Each PSD reduction value is in the range 0 (0dBm/Hz) to
     255 (-127.5dBm/Hz) with steps of 0.5dBm/Hz.  Valid values are
     in the range 0 to 190 (0 to -95dBm/Hz).
     When the number of breakpoints is less than 4, all remaining
     octets are set to the value 0.  Note that the content of this
     object should be correlated with the sub-carriers mask and with
     the RFI setup."
   REFERENCE    "ITU-T G.997.1, paragraph 7.3.1.2"
     ::= { adsl2LineConfProfModeSpecEntry 8 }

adsl2LConfProfPsdMaskSelectUs  OBJECT-TYPE
   SYNTAX      Unsigned32(1..9)
   MAX-ACCESS  read-create
   STATUS      current
   DESCRIPTION
     "The selected upstream PSD mask.  This parameter is used only
      for annexes J and M of G.992.3 and G.992.5, and the same
      selection is used for all relevant enabled bits in
      adsl2LConfProfAtuTransSysEna."
   REFERENCE    "ITU-T G.997.1 (amendment 1), 7.3.1.2.10"
   DEFVAL       { 1 }
    ::= { adsl2LineConfProfModeSpecEntry 9 }

adsl2LConfProfModeSpecRowStatus  OBJECT-TYPE
   SYNTAX      RowStatus
   MAX-ACCESS  read-create
   STATUS      current
   DESCRIPTION

      "This object is used to create a new row or to modify or
      delete an existing row in this table.

      A profile is activated by setting this object to 'active'.
      When 'active' is set, the system will validate the profile.

      Before a profile can be deleted or taken out of service
      (by setting this object to 'destroy' or 'notInService'),
      it must first be unreferenced from all associated
      templates."

   ::= { adsl2LineConfProfModeSpecEntry 10 }

------------------------------------------------
--          adsl2ChConfProfileTable           --
------------------------------------------------
adsl2ChConfProfileTable  OBJECT-TYPE
   SYNTAX      SEQUENCE  OF  Adsl2ChConfProfileEntry
   MAX-ACCESS  not-accessible



   STATUS      current
   DESCRIPTION
      "The table adsl2ChConfProfileTable contains ADSL2 channel
       profile configuration.

       Entries in this table MUST be maintained in a
       persistent manner."
   ::= { adsl2ProfileChannel 1 }

adsl2ChConfProfileEntry  OBJECT-TYPE
   SYNTAX      Adsl2ChConfProfileEntry
   MAX-ACCESS  not-accessible
   STATUS      current
   DESCRIPTION
      "The table adsl2ChConfProfileTable contains ADSL2 channel
       profile configuration.
       A default profile with an index of 'DEFVAL' will
       always exist, and its parameters will be set to vendor-
       specific values, unless otherwise specified in this document."
   INDEX  { adsl2ChConfProfProfileName }
   ::= { adsl2ChConfProfileTable 1 }

Adsl2ChConfProfileEntry  ::=
   SEQUENCE {
      adsl2ChConfProfProfileName          SnmpAdminString,
      adsl2ChConfProfMinDataRateDs        Unsigned32,
      adsl2ChConfProfMinDataRateUs        Unsigned32,
      adsl2ChConfProfMinResDataRateDs     Unsigned32,
      adsl2ChConfProfMinResDataRateUs     Unsigned32,
      adsl2ChConfProfMaxDataRateDs        Unsigned32,
      adsl2ChConfProfMaxDataRateUs        Unsigned32,
      adsl2ChConfProfMinDataRateLowPwrDs  Unsigned32,
      adsl2ChConfProfMaxDelayDs           Unsigned32,
      adsl2ChConfProfMaxDelayUs           Unsigned32,
      adsl2ChConfProfMinProtectionDs      Adsl2SymbolProtection,
      adsl2ChConfProfMinProtectionUs      Adsl2SymbolProtection,
      adsl2ChConfProfMaxBerDs             Adsl2MaxBer,
      adsl2ChConfProfMaxBerUs             Adsl2MaxBer,
      adsl2ChConfProfUsDataRateDs         Unsigned32,
      adsl2ChConfProfDsDataRateDs         Unsigned32,
      adsl2ChConfProfUsDataRateUs         Unsigned32,
      adsl2ChConfProfDsDataRateUs         Unsigned32,
      adsl2ChConfProfImaEnabled           TruthValue,
      adsl2ChConfProfRowStatus            RowStatus
   }

adsl2ChConfProfProfileName  OBJECT-TYPE
   SYNTAX      SnmpAdminString (SIZE(1..32))



   MAX-ACCESS  not-accessible
   STATUS      current
   DESCRIPTION
      "This object identifies a row in this table."
   ::= { adsl2ChConfProfileEntry 1 }

adsl2ChConfProfMinDataRateDs  OBJECT-TYPE
   SYNTAX      Unsigned32(0..200000000)
   UNITS       "bits/second"
   MAX-ACCESS  read-create
   STATUS      current
   DESCRIPTION
      "Minimum Data Rate on Downstream direction.  The minimum net
       data rate for the bearer channel, coded in bits/second."
   REFERENCE    "ITU-T G.997.1, paragraph 7.3.2.1"
   ::= { adsl2ChConfProfileEntry 2 }

adsl2ChConfProfMinDataRateUs  OBJECT-TYPE
   SYNTAX      Unsigned32(0..200000000)
   UNITS       "bits/second"
   MAX-ACCESS  read-create
   STATUS      current
   DESCRIPTION
      "Minimum Data Rate on Upstream direction.  The minimum net data
       rate for the bearer channel, coded in bits/second."
   REFERENCE    "ITU-T G.997.1, paragraph 7.3.2.1"
   ::= { adsl2ChConfProfileEntry 3 }

adsl2ChConfProfMinResDataRateDs  OBJECT-TYPE
   SYNTAX      Unsigned32(0..200000000)
   UNITS       "bits/second"
   MAX-ACCESS  read-create
   STATUS      current
   DESCRIPTION
      "Minimum Reserved Data Rate on Downstream direction.  The
       minimum reserved net data rate for the bearer channel, coded
       in bits/second.  This parameter is used only if the Rate
       Adaptation Mode in the direction of the bearer channel (i.e.,
       adsl2LConfProfRaModeDs) is set to dynamicRa."
   REFERENCE    "ITU-T G.997.1, paragraph 7.3.2.1"
   ::= { adsl2ChConfProfileEntry 4 }

adsl2ChConfProfMinResDataRateUs  OBJECT-TYPE
   SYNTAX      Unsigned32(0..200000000)
   UNITS       "bits/second"
   MAX-ACCESS  read-create
   STATUS      current
   DESCRIPTION



      "Minimum Reserved Data Rate on Upstream direction.  The minimum
       reserved net data rate for the bearer channel, coded in
       bits/second.  This parameter is used only if the Rate
       Adaptation Mode in the direction of the bearer channel (i.e.,
       adsl2LConfProfRaModeUs) is set to dynamicRa."
   REFERENCE    "ITU-T G.997.1, paragraph 7.3.2.1"
   ::= { adsl2ChConfProfileEntry 5 }

adsl2ChConfProfMaxDataRateDs  OBJECT-TYPE
   SYNTAX      Unsigned32(0..200000000)
   UNITS       "bits/second"
   MAX-ACCESS  read-create
   STATUS      current
   DESCRIPTION
      "Maximum Data Rate on Downstream direction.  The maximum net
       data rate for the bearer channel, coded in bits/second."
   REFERENCE    "ITU-T G.997.1, paragraph 7.3.2.1"
   ::= { adsl2ChConfProfileEntry 6 }

adsl2ChConfProfMaxDataRateUs  OBJECT-TYPE
   SYNTAX      Unsigned32(0..200000000)
   UNITS       "bits/second"
   MAX-ACCESS  read-create
   STATUS      current
   DESCRIPTION
      "Maximum Data Rate on Upstream direction.  The maximum net data
       rate for the bearer channel, coded in bits/second."
   REFERENCE    "ITU-T G.997.1, paragraph 7.3.2.1"
   ::= { adsl2ChConfProfileEntry 7 }

adsl2ChConfProfMinDataRateLowPwrDs  OBJECT-TYPE
   SYNTAX      Unsigned32(0..200000000)
   UNITS       "bits/second"
   MAX-ACCESS  read-create
   STATUS      current
   DESCRIPTION
      "Minimum Data Rate in Low Power state on Downstream direction.
       The minimum net data rate for the bearer channel, coded in
       bits/second, during the low power state (L1 in G.992.2, L2 in
       G.992.3)."
   REFERENCE    "ITU-T G.997.1, paragraph 7.3.2.1"
   ::= { adsl2ChConfProfileEntry 8 }

adsl2ChConfProfMaxDelayDs  OBJECT-TYPE
   SYNTAX      Unsigned32(0..63)
   UNITS       "milliseconds"
   MAX-ACCESS  read-create
   STATUS      current



   DESCRIPTION
      "Maximum Interleave Delay on Downstream direction.  The maximum
       one-way interleaving delay introduced by the PMS-TC on
       Downstream direction.  The ATUs shall choose the S (factor)
       and D (depth) values such that the actual one-way interleaving
       delay (adsl2ChStatusActDelay) is as close as possible to,
       but less than or equal to, adsl2ChConfProfMaxDelayDs.  The
       delay is coded in ms, with the value 0 indicating no delay
       bound is being imposed."
   REFERENCE    "ITU-T G.997.1, paragraph 7.3.2.2"
   ::= { adsl2ChConfProfileEntry 9 }

adsl2ChConfProfMaxDelayUs  OBJECT-TYPE
   SYNTAX      Unsigned32(0..63)
   UNITS       "milliseconds"
   MAX-ACCESS  read-create
   STATUS      current
   DESCRIPTION
      "Maximum Interleave Delay on Upstream direction.  The maximum
       one-way interleaving delay introduced by the PMS-TC on
       Upstream direction.  The ATUs shall choose the S (factor) and
       D (depth) values such that the actual one-way interleaving
       delay (adsl2ChStatusActDelay) is as close as possible to,
       but less than or equal to, adsl2ChConfProfMaxDelayUs.  The
       delay is coded in ms, with the value 0 indicating no delay
       bound is being imposed."
   REFERENCE    "ITU-T G.997.1, paragraph 7.3.2.2"
   ::= { adsl2ChConfProfileEntry 10 }

adsl2ChConfProfMinProtectionDs  OBJECT-TYPE
   SYNTAX      Adsl2SymbolProtection
   UNITS       "symbols"
   MAX-ACCESS  read-create
   STATUS      current
   DESCRIPTION
      "Minimum Impulse Noise Protection on Downstream direction.  The
       minimum impulse noise protection for the bearer channel,
       expressed in symbols.  The parameter can take the following
       values: noProtection (i.e., INP not required), halfSymbol
       (i.e., INP length is 1/2 symbol), and 1-16 symbols in steps
       of 1 symbol."
   REFERENCE    "ITU-T G.997.1, paragraph 7.3.2.3"
   DEFVAL       { noProtection }
   ::= { adsl2ChConfProfileEntry 11 }

adsl2ChConfProfMinProtectionUs  OBJECT-TYPE
   SYNTAX      Adsl2SymbolProtection
   UNITS       "symbols"



   MAX-ACCESS  read-create
   STATUS      current
   DESCRIPTION
      "Minimum Impulse Noise Protection on Upstream direction.  The
       minimum impulse noise protection for the bearer channel,
       expressed in symbols.  The parameter can take the following
       values: noProtection (i.e., INP not required), halfSymbol
       (i.e., INP length is 1/2 symbol), and 1-16 symbols in steps
       of 1 symbol."
   REFERENCE    "ITU-T G.997.1, paragraph 7.3.2.3"
   DEFVAL       { noProtection }
   ::= { adsl2ChConfProfileEntry 12 }

adsl2ChConfProfMaxBerDs  OBJECT-TYPE
   SYNTAX      Adsl2MaxBer
   MAX-ACCESS  read-create
   STATUS      current
   DESCRIPTION
      "Maximum Bit Error Ratio on Downstream direction.  The maximum
       bit error ratio for the bearer channel.  The parameter can
       take the following values (for 1E-3, 1E-5 or 1E-7):
          eminus3(1),
          eminus5(2), or
          eminus7(3)."
   REFERENCE    "ITU-T G.997.1, paragraph 7.3.2.4"
   DEFVAL       { eminus5 }
  ::= { adsl2ChConfProfileEntry 13 }

adsl2ChConfProfMaxBerUs  OBJECT-TYPE
   SYNTAX      Adsl2MaxBer
   MAX-ACCESS  read-create
   STATUS      current
   DESCRIPTION
      "Maximum Bit Error Ratio on Upstream direction.  The maximum
       bit error ratio for the bearer channel.  The parameter can
       take the following values (for 1E-3, 1E-5 or 1E-7):
          eminus3(1),
          eminus5(2), or
          eminus7(3)."
   REFERENCE    "ITU-T G.997.1, paragraph 7.3.2.4"
   DEFVAL       { eminus5 }
   ::= { adsl2ChConfProfileEntry 14 }

adsl2ChConfProfUsDataRateDs  OBJECT-TYPE
   SYNTAX      Unsigned32(0..200000000)
   UNITS       "bits/second"
   MAX-ACCESS  read-create
   STATUS      current



   DESCRIPTION
      "Data Rate Threshold Up shift for downstream direction.  An
       'Up-shift rate change' event is triggered when the actual
       downstream data rate exceeds, by more than the threshold, the
       data rate at the last entry into Showtime.  The parameter is
       coded in bits/second."
   REFERENCE    "ITU-T G.997.1, paragraph 7.3.2.6"
   ::= { adsl2ChConfProfileEntry 15 }

adsl2ChConfProfDsDataRateDs  OBJECT-TYPE
   SYNTAX      Unsigned32(0..200000000)
   UNITS       "bits/second"
   MAX-ACCESS  read-create
   STATUS      current
   DESCRIPTION
      "Data Rate Threshold Down-shift for downstream direction.  A
       'Down-shift rate change' event is triggered when the actual
       downstream data rate is below the data rate at the last entry
       into Showtime, by more than the threshold.  The parameter is
       coded in bits/second."
   REFERENCE    "ITU-T G.997.1, paragraph 7.3.2.6"
   ::= { adsl2ChConfProfileEntry 16 }

adsl2ChConfProfUsDataRateUs  OBJECT-TYPE
   SYNTAX      Unsigned32(0..200000000)
   UNITS       "bits/second"
   MAX-ACCESS  read-create
   STATUS      current
   DESCRIPTION
      "Data Rate Threshold Up shift for upstream direction.  An
       'Up-shift rate change' event is triggered when the actual
       upstream data rate exceeds, by more than the threshold, the
       data rate at the last entry into Showtime.  The parameter is
       coded in bits/second."
   REFERENCE    "ITU-T G.997.1, paragraph 7.3.2.6"
   ::= { adsl2ChConfProfileEntry 17 }

adsl2ChConfProfDsDataRateUs  OBJECT-TYPE
   SYNTAX      Unsigned32(0..200000000)
   UNITS       "bits/second"
   MAX-ACCESS  read-create
   STATUS      current
   DESCRIPTION
      "Data Rate Threshold Down-shift for upstream direction.  A
       'Down-shift rate change' event is triggered when the actual
       upstream data rate is below the data rate at the last entry
       into Showtime, by more than the threshold.  The parameter is
       coded in bits/second."



   REFERENCE    "ITU-T G.997.1, paragraph 7.3.2.6"
   ::= { adsl2ChConfProfileEntry 18 }

adsl2ChConfProfImaEnabled  OBJECT-TYPE
   SYNTAX      TruthValue
   MAX-ACCESS  read-create
   STATUS      current
   DESCRIPTION
      "IMA Mode Enable.  The parameter enables the IMA operation mode
       in the ATM Data Path.  Relevant only if the channel is an ATM
       Data Path.  When in 'enable' state, the ATM data path should
       comply with the requirements for IMA transmission."
   REFERENCE    "ITU-T G.997.1, paragraph 7.3.4.1"
   DEFVAL       { false }
 ::= { adsl2ChConfProfileEntry 19 }

adsl2ChConfProfRowStatus  OBJECT-TYPE
   SYNTAX      RowStatus
   MAX-ACCESS  read-create
   STATUS      current
   DESCRIPTION
      "This object is used to create a new row or to modify or
      delete an existing row in this table.

      A profile is activated by setting this object to 'active'.
      When 'active' is set, the system will validate the profile.

      Before a profile can be deleted or taken out of service
      (by setting this object to 'destroy' or 'notInService'),
      it must first be unreferenced from all associated
      templates."
   ::= { adsl2ChConfProfileEntry 20 }

------------------------------------------------
--        adsl2LineAlarmConfTemplateTable          --
------------------------------------------------
adsl2LineAlarmConfTemplateTable  OBJECT-TYPE
   SYNTAX      SEQUENCE  OF  Adsl2LineAlarmConfTemplateEntry
   MAX-ACCESS  not-accessible
   STATUS      current
   DESCRIPTION
      "The table adsl2LineAlarmConfTemplateTable contains
       ADSL2 line configuration templates.

       Entries in this table MUST be maintained in a
       persistent manner."
   ::= { adsl2ProfileAlarmConf 1 }




adsl2LineAlarmConfTemplateEntry  OBJECT-TYPE
   SYNTAX      Adsl2LineAlarmConfTemplateEntry
   MAX-ACCESS  not-accessible
   STATUS      current
   DESCRIPTION
      "The table adsl2LineAlarmConfTemplateTable contains ADSL2
      line PM thresholds templates.
      A default template with an index of 'DEFVAL' will
      always exist, and its parameters will be set to vendor-
      specific values, unless otherwise specified in this
      document."
   INDEX  { adsl2LAlarmConfTempTemplateName }
   ::= { adsl2LineAlarmConfTemplateTable 1 }

Adsl2LineAlarmConfTemplateEntry  ::=
   SEQUENCE {
      adsl2LAlarmConfTempTemplateName      SnmpAdminString,
      adsl2LAlarmConfTempLineProfile       SnmpAdminString,
      adsl2LAlarmConfTempChan1ConfProfile  SnmpAdminString,
      adsl2LAlarmConfTempChan2ConfProfile  SnmpAdminString,
      adsl2LAlarmConfTempChan3ConfProfile  SnmpAdminString,
      adsl2LAlarmConfTempChan4ConfProfile  SnmpAdminString,
      adsl2LAlarmConfTempRowStatus         RowStatus
   }

adsl2LAlarmConfTempTemplateName  OBJECT-TYPE
   SYNTAX      SnmpAdminString (SIZE(1..32))
   MAX-ACCESS  not-accessible
   STATUS      current
   DESCRIPTION
      "This object identifies a row in this table."
   ::= { adsl2LineAlarmConfTemplateEntry 1 }

adsl2LAlarmConfTempLineProfile  OBJECT-TYPE
   SYNTAX      SnmpAdminString (SIZE(1..32))
   MAX-ACCESS  read-create
   STATUS      current
   DESCRIPTION
      "The value of this object identifies the row in the ADSL2 Line
       Thresholds Configuration Profile Table
       (adsl2LineAlarmConfProfileTable) that applies to this ADSL2
       line."
   REFERENCE    "DSL Forum TR-90, paragraph 5.4.1"
   DEFVAL       { "DEFVAL" }
   ::= { adsl2LineAlarmConfTemplateEntry 2 }

adsl2LAlarmConfTempChan1ConfProfile  OBJECT-TYPE
   SYNTAX      SnmpAdminString (SIZE(1..32))



   MAX-ACCESS  read-create
   STATUS      current
   DESCRIPTION
      "The value of this object identifies the row in the ADSL2
       Channel Thresholds Configuration Profile Table
       (adsl2ChAlarmConfProfileTable) that applies for ADSL2
       bearer channel #1.  The channel profile name specified here
       must match the name of an existing row in the
       adsl2ChAlarmConfProfileTable table."
   REFERENCE    "DSL Forum TR-90, paragraph 5.4.1"
   DEFVAL       { "DEFVAL" }
   ::= { adsl2LineAlarmConfTemplateEntry 3 }

adsl2LAlarmConfTempChan2ConfProfile  OBJECT-TYPE
   SYNTAX      SnmpAdminString (SIZE(0..32))
   MAX-ACCESS  read-create
   STATUS      current
   DESCRIPTION
      "The value of this object identifies the row in the ADSL2
       Channel Thresholds Configuration Profile Table
       (adsl2ChAlarmConfProfileTable) that applies for ADSL2
       bearer channel #2.  The channel profile name specified here
       must match the name of an existing row in the
       adsl2ChAlarmConfProfileTable table.  If the channel is unused,
       then the object is set to a zero-length string."
   REFERENCE    "DSL Forum TR-90, paragraph 5.4.1"
   DEFVAL       { "" }
   ::= { adsl2LineAlarmConfTemplateEntry 4 }

adsl2LAlarmConfTempChan3ConfProfile  OBJECT-TYPE
   SYNTAX      SnmpAdminString (SIZE(0..32))
   MAX-ACCESS  read-create
   STATUS      current
   DESCRIPTION
      "The value of this object identifies the row in the ADSL2
       Channel Thresholds Configuration Profile Table
       (adsl2ChAlarmConfProfileTable) that applies for ADSL2
       bearer channel #3.  The channel profile name specified here
       must match the name of an existing row in the
       adsl2ChAlarmConfProfileTable table.
       This object may be set to a non-zero-length string only if
       adsl2LAlarmConfTempChan2ConfProfile contains a non-zero-
       length string."
   REFERENCE    "DSL Forum TR-90, paragraph 5.4.1"
   DEFVAL       { "" }
   ::= { adsl2LineAlarmConfTemplateEntry 5 }

adsl2LAlarmConfTempChan4ConfProfile  OBJECT-TYPE



   SYNTAX      SnmpAdminString (SIZE(0..32))
   MAX-ACCESS  read-create
   STATUS      current
   DESCRIPTION
      "The value of this object identifies the row in the ADSL2
       Channel Thresholds Configuration Profile Table
       (adsl2ChAlarmConfProfileTable) that applies for ADSL2
       bearer channel #4.  The channel profile name specified here
       must match the name of an existing row in the
       adsl2ChAlarmConfProfileTable table.
       This object may be set to a non-zero-length string only if
       adsl2LAlarmConfTempChan3ConfProfile contains a non-zero-
       length string."
   REFERENCE    "DSL Forum TR-90, paragraph 5.4.1"
   DEFVAL       { "" }
   ::= { adsl2LineAlarmConfTemplateEntry 6 }

adsl2LAlarmConfTempRowStatus  OBJECT-TYPE
   SYNTAX      RowStatus
   MAX-ACCESS  read-create
   STATUS      current
   DESCRIPTION
      "This object is used to create a new row or to modify or
      delete an existing row in this table.

      A template is activated by setting this object to 'active'.
      When 'active' is set, the system will validate the template.

      Before a template can be deleted or taken out of service
      (by setting this object to 'destroy' or 'notInService'),
      it must first be unreferenced from all associated
      lines."
   ::= { adsl2LineAlarmConfTemplateEntry 7 }

------------------------------------------------
--      adsl2LineAlarmConfProfileTable        --
------------------------------------------------

adsl2LineAlarmConfProfileTable  OBJECT-TYPE
     SYNTAX      SEQUENCE  OF  Adsl2LineAlarmConfProfileEntry
     MAX-ACCESS  not-accessible
     STATUS      current
     DESCRIPTION
      "The table adsl2LineAlarmConfProfileTable contains ADSL2
      line PM thresholds profiles.

       Entries in this table MUST be maintained in a
       persistent manner."



     ::= { adsl2ProfileAlarmConf 2 }

adsl2LineAlarmConfProfileEntry  OBJECT-TYPE
     SYNTAX      Adsl2LineAlarmConfProfileEntry
     MAX-ACCESS  not-accessible
     STATUS      current
     DESCRIPTION
      "The table adsl2LineAlarmConfProfileTable contains ADSL2
      line PM thresholds profiles.
      A default profile with an index of 'DEFVAL' will
      always exist, and its parameters will be set to vendor-
      specific values, unless otherwise specified in this
      document."
     INDEX  { adsl2LineAlarmConfProfileName }
     ::= { adsl2LineAlarmConfProfileTable 1 }

Adsl2LineAlarmConfProfileEntry ::=
     SEQUENCE {
     adsl2LineAlarmConfProfileName                SnmpAdminString,
     adsl2LineAlarmConfProfileAtucThresh15MinFecs
                                          HCPerfIntervalThreshold,
     adsl2LineAlarmConfProfileAtucThresh15MinEs
                                          HCPerfIntervalThreshold,
     adsl2LineAlarmConfProfileAtucThresh15MinSes
                                           HCPerfIntervalThreshold,
     adsl2LineAlarmConfProfileAtucThresh15MinLoss
                                           HCPerfIntervalThreshold,
     adsl2LineAlarmConfProfileAtucThresh15MinUas
                                           HCPerfIntervalThreshold,
     adsl2LineAlarmConfProfileAturThresh15MinFecs
                                           HCPerfIntervalThreshold,
     adsl2LineAlarmConfProfileAturThresh15MinEs
                                           HCPerfIntervalThreshold,
     adsl2LineAlarmConfProfileAturThresh15MinSes
                                           HCPerfIntervalThreshold,
     adsl2LineAlarmConfProfileAturThresh15MinLoss
                                           HCPerfIntervalThreshold,
     adsl2LineAlarmConfProfileAturThresh15MinUas
                                           HCPerfIntervalThreshold,

     adsl2LineAlarmConfProfileThresh15MinFailedFullInt   Unsigned32,
     adsl2LineAlarmConfProfileThresh15MinFailedShrtInt   Unsigned32,

     adsl2LineAlarmConfProfileRowStatus                   RowStatus
     }

adsl2LineAlarmConfProfileName  OBJECT-TYPE
     SYNTAX      SnmpAdminString (SIZE(1..32))



     MAX-ACCESS  not-accessible
     STATUS      current
     DESCRIPTION
     "This object identifies a row in this table."
     ::= { adsl2LineAlarmConfProfileEntry 1 }

adsl2LineAlarmConfProfileAtucThresh15MinFecs  OBJECT-TYPE
     SYNTAX      HCPerfIntervalThreshold
     UNITS       "seconds"
     MAX-ACCESS  read-create
     STATUS      current
     DESCRIPTION
     "A threshold for the adsl2PMLCurr15MFecs counter,
     when adsl2PMLCurrUnit is atuc(1).
     The value 0 means that no threshold is specified for the
     associated counter."
   REFERENCE    "ITU-T G.997.1, paragraph 7.3.1"
   DEFVAL       { 0 }
     ::= { adsl2LineAlarmConfProfileEntry 2 }

adsl2LineAlarmConfProfileAtucThresh15MinEs  OBJECT-TYPE
     SYNTAX      HCPerfIntervalThreshold
     UNITS       "seconds"
     MAX-ACCESS  read-create
     STATUS      current
     DESCRIPTION
     "A threshold for the adsl2PMLCurr15MEs counter,
     when adsl2PMLCurrUnit is atuc(1).
     The value 0 means that no threshold is specified for the
     associated counter."
   REFERENCE    "ITU-T G.997.1, paragraph 7.3.1"
   DEFVAL       { 0 }
     ::= { adsl2LineAlarmConfProfileEntry 3 }

adsl2LineAlarmConfProfileAtucThresh15MinSes  OBJECT-TYPE
     SYNTAX      HCPerfIntervalThreshold
     UNITS       "seconds"
     MAX-ACCESS  read-create
     STATUS      current
     DESCRIPTION
     "A threshold for the adsl2PMLCurr15MSes counter,
     when adsl2PMLCurrUnit is atuc(1).
     The value 0 means that no threshold is specified for the
     associated counter."
   REFERENCE    "ITU-T G.997.1, paragraph 7.3.1"
   DEFVAL       { 0 }
     ::= { adsl2LineAlarmConfProfileEntry 4 }




adsl2LineAlarmConfProfileAtucThresh15MinLoss  OBJECT-TYPE
     SYNTAX      HCPerfIntervalThreshold
     UNITS       "seconds"
     MAX-ACCESS  read-create
     STATUS      current
     DESCRIPTION
     "A threshold for the adsl2PMLCurr15MLoss counter,
     when adsl2PMLCurrUnit is atuc(1).
     The value 0 means that no threshold is specified for the
     associated counter."
   REFERENCE    "ITU-T G.997.1, paragraph 7.3.1"
   DEFVAL       { 0 }
     ::= { adsl2LineAlarmConfProfileEntry 5 }

adsl2LineAlarmConfProfileAtucThresh15MinUas  OBJECT-TYPE
     SYNTAX      HCPerfIntervalThreshold
     UNITS       "seconds"
     MAX-ACCESS  read-create
     STATUS      current
     DESCRIPTION
     "A threshold for the adsl2PMLCurr15MUas counter,
     when adsl2PMLCurrUnit is atuc(1).
     The value 0 means that no threshold is specified for the
     associated counter."
   REFERENCE    "ITU-T G.997.1, paragraph 7.3.1"
   DEFVAL       { 0 }
     ::= { adsl2LineAlarmConfProfileEntry 6 }

adsl2LineAlarmConfProfileAturThresh15MinFecs  OBJECT-TYPE
     SYNTAX      HCPerfIntervalThreshold
     UNITS       "seconds"
     MAX-ACCESS  read-create
     STATUS      current
     DESCRIPTION
     "A threshold for the adsl2PMLCurr15MFecs counter,
     when adsl2PMLCurrUnit is atur(2).
     The value 0 means that no threshold is specified for the
     associated counter."
   REFERENCE    "ITU-T G.997.1, paragraph 7.3.1"
   DEFVAL       { 0 }
     ::= { adsl2LineAlarmConfProfileEntry 7 }

adsl2LineAlarmConfProfileAturThresh15MinEs  OBJECT-TYPE
     SYNTAX      HCPerfIntervalThreshold
     UNITS       "seconds"
     MAX-ACCESS  read-create
     STATUS      current
     DESCRIPTION



     "A threshold for the adsl2PMLCurr15MEs counter,
     when adsl2PMLCurrUnit is atur(2).
     The value 0 means that no threshold is specified for the
     associated counter."
   REFERENCE    "ITU-T G.997.1, paragraph 7.3.1"
   DEFVAL       { 0 }
     ::= { adsl2LineAlarmConfProfileEntry 8 }

adsl2LineAlarmConfProfileAturThresh15MinSes  OBJECT-TYPE
     SYNTAX      HCPerfIntervalThreshold
     UNITS       "seconds"
     MAX-ACCESS  read-create
     STATUS      current
     DESCRIPTION
     "A threshold for the adsl2PMLCurr15MSes counter,
     when adsl2PMLCurrUnit is atur(2).
     The value 0 means that no threshold is specified for the
     associated counter."
   REFERENCE    "ITU-T G.997.1, paragraph 7.3.1"
   DEFVAL       { 0 }
     ::= { adsl2LineAlarmConfProfileEntry 9 }

adsl2LineAlarmConfProfileAturThresh15MinLoss  OBJECT-TYPE
     SYNTAX      HCPerfIntervalThreshold
     UNITS       "seconds"
     MAX-ACCESS  read-create
     STATUS      current
     DESCRIPTION
     "A threshold for the adsl2PMLCurr15MLoss counter,
     when adsl2PMLCurrUnit is atur(2).
     The value 0 means that no threshold is specified for the
     associated counter."
   REFERENCE    "ITU-T G.997.1, paragraph 7.3.1"
   DEFVAL       { 0 }
     ::= { adsl2LineAlarmConfProfileEntry 10 }

adsl2LineAlarmConfProfileAturThresh15MinUas  OBJECT-TYPE
     SYNTAX      HCPerfIntervalThreshold
     UNITS       "seconds"
     MAX-ACCESS  read-create
     STATUS      current
     DESCRIPTION
     "A threshold for the adsl2PMLCurr15MUas counter,
     when adsl2PMLCurrUnit is atur(2).
     The value 0 means that no threshold is specified for the
     associated counter."
   REFERENCE    "ITU-T G.997.1, paragraph 7.3.1"
   DEFVAL       { 0 }



     ::= { adsl2LineAlarmConfProfileEntry 11 }

adsl2LineAlarmConfProfileThresh15MinFailedFullInt  OBJECT-TYPE
     SYNTAX      Unsigned32
     MAX-ACCESS  read-create
     STATUS      current
     DESCRIPTION
     "A threshold for the adsl2PMLCurrInit15MfailedFullInits
     counter.
     The value 0 means that no threshold is specified for the
     associated counter."
   REFERENCE    "ITU-T G.997.1, paragraph 7.3.1"
   DEFVAL       { 0 }
     ::= { adsl2LineAlarmConfProfileEntry 12 }

adsl2LineAlarmConfProfileThresh15MinFailedShrtInt  OBJECT-TYPE
     SYNTAX      Unsigned32
     MAX-ACCESS  read-create
     STATUS      current
     DESCRIPTION
     "A threshold for the adsl2PMLCurrInit15MFailedShortInits
     counter.
     The value 0 means that no threshold is specified for the
     associated counter."
   REFERENCE    "ITU-T G.997.1, paragraph 7.3.1"
   DEFVAL       { 0 }
     ::= { adsl2LineAlarmConfProfileEntry 13 }

adsl2LineAlarmConfProfileRowStatus  OBJECT-TYPE
     SYNTAX      RowStatus
     MAX-ACCESS  read-create
     STATUS      current
     DESCRIPTION
      "This object is used to create a new row or to modify or
      delete an existing row in this table.

      A profile is activated by setting this object to 'active'.
      When 'active' is set, the system will validate the profile.

      Before a profile can be deleted or taken out of service
      (by setting this object to 'destroy' or 'notInService'),
      it must first be unreferenced from all associated
      templates."
     ::= { adsl2LineAlarmConfProfileEntry 14 }


------------------------------------------------
--      adsl2ChAlarmConfProfileTable        --



------------------------------------------------

adsl2ChAlarmConfProfileTable  OBJECT-TYPE
     SYNTAX      SEQUENCE  OF  Adsl2ChAlarmConfProfileEntry
     MAX-ACCESS  not-accessible
     STATUS      current
     DESCRIPTION
      "The table adsl2ChAlarmConfProfileTable contains ADSL2
      channel PM thresholds profiles.

       Entries in this table MUST be maintained in a
       persistent manner."
     ::= { adsl2ProfileAlarmConf 3 }

adsl2ChAlarmConfProfileEntry  OBJECT-TYPE
     SYNTAX      Adsl2ChAlarmConfProfileEntry
     MAX-ACCESS  not-accessible
     STATUS      current
     DESCRIPTION
      "The table adsl2ChAlarmConfProfileTable contains ADSL2
      channel PM thresholds profiles.
      A default profile with an index of 'DEFVAL' will
      always exist, and its parameters will be set to vendor-
      specific values, unless otherwise specified in this document."
     INDEX  { adsl2ChAlarmConfProfileName }
     ::= { adsl2ChAlarmConfProfileTable 1 }

Adsl2ChAlarmConfProfileEntry ::=
     SEQUENCE {
     adsl2ChAlarmConfProfileName
                                                     SnmpAdminString,
     adsl2ChAlarmConfProfileAtucThresh15MinCodingViolations
                                                     Unsigned32,
     adsl2ChAlarmConfProfileAtucThresh15MinCorrected Unsigned32,
     adsl2ChAlarmConfProfileAturThresh15MinCodingViolations
                                                     Unsigned32,
     adsl2ChAlarmConfProfileAturThresh15MinCorrected Unsigned32,
     adsl2ChAlarmConfProfileRowStatus                RowStatus
     }

adsl2ChAlarmConfProfileName  OBJECT-TYPE
     SYNTAX      SnmpAdminString (SIZE(1..32))
     MAX-ACCESS  not-accessible
     STATUS      current
     DESCRIPTION
     "This object identifies a row in this table."
     ::= { adsl2ChAlarmConfProfileEntry 1 }




adsl2ChAlarmConfProfileAtucThresh15MinCodingViolations OBJECT-TYPE
     SYNTAX      Unsigned32
     MAX-ACCESS  read-create
     STATUS      current
     DESCRIPTION
     "A threshold for the adsl2PMChCurr15MCodingViolations
     counter, when adsl2PMChCurrUnit is atuc(1).
     The value 0 means that no threshold is specified for the
     associated counter."
   REFERENCE    "ITU-T G.997.1, paragraph 7.3.2"
   DEFVAL       { 0 }
     ::= { adsl2ChAlarmConfProfileEntry 2 }

adsl2ChAlarmConfProfileAtucThresh15MinCorrected  OBJECT-TYPE
     SYNTAX      Unsigned32
     MAX-ACCESS  read-create
     STATUS      current
     DESCRIPTION
     "A threshold for the adsl2PMChCurr15MCorrectedBlocks
     counter, when adsl2PMChCurrUnit is atuc(1).
     The value 0 means that no threshold is specified for the
     associated counter."
   REFERENCE    "ITU-T G.997.1, paragraph 7.3.2"
   DEFVAL       { 0 }
     ::= { adsl2ChAlarmConfProfileEntry 3 }

adsl2ChAlarmConfProfileAturThresh15MinCodingViolations  OBJECT-TYPE
     SYNTAX      Unsigned32
     MAX-ACCESS  read-create
     STATUS      current
     DESCRIPTION
     "A threshold for the adsl2PMChCurr15MCodingViolations
     counter, when adsl2PMChCurrUnit is atur(2).
     The value 0 means that no threshold is specified for the
     associated counter."
   REFERENCE    "ITU-T G.997.1, paragraph 7.3.2"
   DEFVAL       { 0 }
     ::= { adsl2ChAlarmConfProfileEntry 4 }

adsl2ChAlarmConfProfileAturThresh15MinCorrected  OBJECT-TYPE
     SYNTAX      Unsigned32
     MAX-ACCESS  read-create
     STATUS      current
     DESCRIPTION
     "A threshold for the adsl2PMChCurr15MCorrectedBlocks
     counter, when adsl2PMChCurrUnit is atur(2).
     The value 0 means that no threshold is specified for the
     associated counter."



   REFERENCE    "ITU-T G.997.1, paragraph 7.3.2"
   DEFVAL       { 0 }
     ::= { adsl2ChAlarmConfProfileEntry 5 }

adsl2ChAlarmConfProfileRowStatus  OBJECT-TYPE
     SYNTAX      RowStatus
     MAX-ACCESS  read-create
     STATUS      current
     DESCRIPTION
      "This object is used to create a new row or to modify or
      delete an existing row in this table.

      A profile is activated by setting this object to 'active'.
      When 'active' is set, the system will validate the profile.

      Before a profile can be deleted or taken out of service
      (by setting this object to 'destroy' or 'notInService'),
      it must first be unreferenced from all associated
      templates."
     ::= { adsl2ChAlarmConfProfileEntry 6 }

------------------------------------------------
--          PM line current counters          --
------------------------------------------------
adsl2PMLineCurrTable  OBJECT-TYPE
   SYNTAX      SEQUENCE  OF  Adsl2PMLineCurrEntry
   MAX-ACCESS  not-accessible
   STATUS      current
   DESCRIPTION
      "The table adsl2PMLineCurrTable contains current Performance
       Monitoring results of ADSL2 lines."
   ::= { adsl2PMLine 1 }

adsl2PMLineCurrEntry  OBJECT-TYPE
   SYNTAX      Adsl2PMLineCurrEntry
   MAX-ACCESS  not-accessible
   STATUS      current
   DESCRIPTION
      "The table adsl2PMLineCurrTable contains current Performance
       Monitoring results of ADSL2 lines.
       The index of this table consists of an interface index, where
       the interface has an ifType of adsl2plus(238), along with a
       termination unit.
       The PM counters in the table are not reset even when the XTU
       is reinitialized.  They are reinitialized only when the
       agent itself is reset or reinitialized."
   INDEX  { ifIndex, adsl2PMLCurrUnit }
   ::= { adsl2PMLineCurrTable 1 }



Adsl2PMLineCurrEntry  ::=
   SEQUENCE {
      adsl2PMLCurrUnit                    Adsl2Unit,
      adsl2PMLCurrValidIntervals          Unsigned32,
      adsl2PMLCurrInvalidIntervals        Unsigned32,
      adsl2PMLCurr15MTimeElapsed          HCPerfTimeElapsed,
      adsl2PMLCurr15MFecs                 Counter32,
      adsl2PMLCurr15MEs                   Counter32,
      adsl2PMLCurr15MSes                  Counter32,
      adsl2PMLCurr15MLoss                 Counter32,
      adsl2PMLCurr15MUas                  Counter32,
      adsl2PMLCurr1DayValidIntervals      Unsigned32,
      adsl2PMLCurr1DayInvalidIntervals    Unsigned32,
      adsl2PMLCurr1DayTimeElapsed         HCPerfTimeElapsed,
      adsl2PMLCurr1DayFecs                Counter32,
      adsl2PMLCurr1DayEs                  Counter32,
      adsl2PMLCurr1DaySes                 Counter32,
      adsl2PMLCurr1DayLoss                Counter32,
      adsl2PMLCurr1DayUas                 Counter32
   }

adsl2PMLCurrUnit  OBJECT-TYPE
   SYNTAX      Adsl2Unit
   MAX-ACCESS  not-accessible
   STATUS      current
   DESCRIPTION
      "The termination unit atuc(1) or atur(2)."
   ::= { adsl2PMLineCurrEntry 1 }

adsl2PMLCurrValidIntervals  OBJECT-TYPE
   SYNTAX      Unsigned32
   MAX-ACCESS  read-only
   STATUS      current
   DESCRIPTION
      "Valid intervals."
   ::= { adsl2PMLineCurrEntry 2 }

adsl2PMLCurrInvalidIntervals  OBJECT-TYPE
   SYNTAX      Unsigned32
   MAX-ACCESS  read-only
   STATUS      current
   DESCRIPTION
      "Invalid intervals."
   ::= { adsl2PMLineCurrEntry 3 }

adsl2PMLCurr15MTimeElapsed  OBJECT-TYPE
   SYNTAX      HCPerfTimeElapsed
   UNITS       "seconds"



   MAX-ACCESS  read-only
   STATUS      current
   DESCRIPTION
      "Total elapsed seconds since this PM interval began.
       Note that the PM counters are not reset even when the XTU
       is reinitialized.  They are reinitialized only when the
       agent itself is reset or reinitialized."
   ::= { adsl2PMLineCurrEntry 4 }

adsl2PMLCurr15MFecs  OBJECT-TYPE
   SYNTAX      Counter32
   UNITS       "seconds"
   MAX-ACCESS  read-only
   STATUS      current
   DESCRIPTION
      "Count of seconds during this interval where there was at least
       one FEC correction event for one or more bearer channels in
       this line.  This parameter is inhibited during UAS or SES."
   REFERENCE    "ITU-T G.997.1, paragraph 7.2.1"
   ::= { adsl2PMLineCurrEntry 5 }

adsl2PMLCurr15MEs  OBJECT-TYPE
   SYNTAX      Counter32
   UNITS       "seconds"
   MAX-ACCESS  read-only
   STATUS      current
   DESCRIPTION
      "Count of seconds during this interval where there was:
          ATU-C: CRC-8 >= 1 for one or more bearer channels OR
                 LOS >= 1 OR SEF >=1 OR LPR >= 1
          ATU-R: FEBE >= 1 for one or more bearer channels OR
                 LOS-FE >=1 OR RDI >=1 OR LPR-FE >=1 .
       This parameter is inhibited during UAS."
   REFERENCE    "ITU-T G.997.1, paragraph 7.2.1"
   ::= { adsl2PMLineCurrEntry 6 }

adsl2PMLCurr15MSes  OBJECT-TYPE
   SYNTAX      Counter32
   UNITS       "seconds"
   MAX-ACCESS  read-only
   STATUS      current
   DESCRIPTION
      "Count of seconds during this interval where there was:
          ATU-C: (CRC-8 summed over all bearer channels) >= 18 OR
                 LOS >= 1 OR SEF >= 1 OR LPR >= 1
          ATU-R: (FEBE summed over all bearer channels) >= 18 OR
                 LOS-FE >= 1 OR RDI >= 1 OR LPR-FE >= 1 .
       This parameter is inhibited during UAS."



   REFERENCE    "ITU-T G.997.1, paragraph 7.2.1"
   ::= { adsl2PMLineCurrEntry 7 }

adsl2PMLCurr15MLoss  OBJECT-TYPE
   SYNTAX      Counter32
   UNITS       "seconds"
   MAX-ACCESS  read-only
   STATUS      current
   DESCRIPTION
      "Count of seconds during this interval where there was LOS (or
       LOS-FE for ATU-R)."
   REFERENCE    "ITU-T G.997.1, paragraph 7.2.1"
   ::= { adsl2PMLineCurrEntry 8 }

adsl2PMLCurr15MUas  OBJECT-TYPE
   SYNTAX      Counter32
   UNITS       "seconds"
   MAX-ACCESS  read-only
   STATUS      current
   DESCRIPTION
      "Count of seconds in Unavailability State during this
       interval.  Unavailability begins at the onset of 10
       contiguous severely-errored seconds, and ends at the
       onset of 10 contiguous seconds with no severely-errored
       seconds."
   REFERENCE    "ITU-T G.997.1, paragraph 7.2.1"
   ::= { adsl2PMLineCurrEntry 9 }

adsl2PMLCurr1DayValidIntervals  OBJECT-TYPE
   SYNTAX      Unsigned32
   MAX-ACCESS  read-only
   STATUS      current
   DESCRIPTION
      "Valid intervals."
   ::= { adsl2PMLineCurrEntry 10 }

adsl2PMLCurr1DayInvalidIntervals  OBJECT-TYPE
   SYNTAX      Unsigned32
   MAX-ACCESS  read-only
   STATUS      current
   DESCRIPTION
      "Invalid intervals."
   ::= { adsl2PMLineCurrEntry 11 }

adsl2PMLCurr1DayTimeElapsed  OBJECT-TYPE
   SYNTAX      HCPerfTimeElapsed
   UNITS       "seconds"
   MAX-ACCESS  read-only



   STATUS      current
   DESCRIPTION
      "Total elapsed seconds since this PM interval began.
       Note that the PM counters are not reset even when the XTU
       is reinitialized.  They are reinitialized only when the
       agent itself is reset or reinitialized."
   ::= { adsl2PMLineCurrEntry 12 }

adsl2PMLCurr1DayFecs  OBJECT-TYPE
   SYNTAX      Counter32
   UNITS       "seconds"
   MAX-ACCESS  read-only
   STATUS      current
   DESCRIPTION
      "Count of seconds during this interval where there was at least
       one FEC correction event for one or more bearer channels in
       this line.  This parameter is inhibited during UAS or SES."
   REFERENCE    "ITU-T G.997.1, paragraph 7.2.1"
   ::= { adsl2PMLineCurrEntry 13 }

adsl2PMLCurr1DayEs  OBJECT-TYPE
   SYNTAX      Counter32
   UNITS       "seconds"
   MAX-ACCESS  read-only
   STATUS      current
   DESCRIPTION
      "Count of seconds during this interval where there was:
          ATU-C: CRC-8 >= 1 for one or more bearer channels OR
                 LOS >= 1 OR SEF >= 1 OR LPR >= 1
          ATU-R: FEBE >= 1 for one or more bearer channels OR
                 LOS-FE >= 1 OR RDI >= 1 OR LPR-FE >= 1.
       This parameter is inhibited during UAS."
   REFERENCE    "ITU-T G.997.1, paragraph 7.2.1"
   ::= { adsl2PMLineCurrEntry 14 }

adsl2PMLCurr1DaySes  OBJECT-TYPE
   SYNTAX      Counter32
   UNITS       "seconds"
   MAX-ACCESS  read-only
   STATUS      current
   DESCRIPTION
      "Count of seconds during this interval where there was:
          ATU-C: (CRC-8 summed over all bearer channels) >= 18 OR
                  LOS >= 1 OR SEF >= 1 OR LPR >= 1
          ATU-R: (FEBE summed over all bearer channels) >= 18 OR
                 LOS-FE >= 1 OR RDI >= 1 OR LPR-FE >= 1
       This parameter is inhibited during UAS."
   REFERENCE    "ITU-T G.997.1, paragraph 7.2.1"



   ::= { adsl2PMLineCurrEntry 15 }

adsl2PMLCurr1DayLoss  OBJECT-TYPE
   SYNTAX      Counter32
   UNITS       "seconds"
   MAX-ACCESS  read-only
   STATUS      current
   DESCRIPTION
      "Count of seconds during this interval where there was LOS (or
       LOS-FE for ATU-R)."
   REFERENCE    "ITU-T G.997.1, paragraph 7.2.1"
   ::= { adsl2PMLineCurrEntry 16 }

adsl2PMLCurr1DayUas  OBJECT-TYPE
   SYNTAX      Counter32
   UNITS       "seconds"
   MAX-ACCESS  read-only
   STATUS      current
   DESCRIPTION
      "Count of seconds in Unavailability State during this interval.
       Unavailability begins at the onset of 10 contiguous severely-
       errored seconds, and ends at the onset of 10 contiguous
       seconds with no severely-errored seconds."
   REFERENCE    "ITU-T G.997.1, paragraph 7.2.1"
   ::= { adsl2PMLineCurrEntry 17 }


------------------------------------------------
--          PM line init current counters     --
------------------------------------------------

adsl2PMLineCurrInitTable   OBJECT-TYPE
   SYNTAX      SEQUENCE  OF  Adsl2PMLineCurrInitEntry
   MAX-ACCESS  not-accessible
   STATUS      current
   DESCRIPTION
      "The table adsl2PMLineCurrInitTable contains current
       initialization counters of the ADSL2 line.
       The PM counters in the table are not reset even when the XTU
       is reinitialized.  They are reinitialized only when the
       agent itself is reset or reinitialized."
   ::= { adsl2PMLine 2 }

adsl2PMLineCurrInitEntry  OBJECT-TYPE
   SYNTAX      Adsl2PMLineCurrInitEntry
   MAX-ACCESS  not-accessible
   STATUS      current
   DESCRIPTION



      "The table adsl2PMLineCurrInitTable contains current
       initialization counters of the ADSL2 line.
       The index of this table consists of an interface index, where
       the interface has an ifType of adsl2plus(238), and a
       termination unit."
   INDEX  { ifIndex }
   ::= { adsl2PMLineCurrInitTable 1 }

Adsl2PMLineCurrInitEntry  ::=
   SEQUENCE {
      adsl2PMLCurrInit15MTimeElapsed          Unsigned32,
      adsl2PMLCurrInit15MFullInits            Unsigned32,
      adsl2PMLCurrInit15MFailedFullInits      Unsigned32,
      adsl2PMLCurrInit15MShortInits           Unsigned32,
      adsl2PMLCurrInit15MFailedShortInits     Unsigned32,
      adsl2PMLCurrInit1DayTimeElapsed         Unsigned32,
      adsl2PMLCurrInit1DayFullInits           Unsigned32,
      adsl2PMLCurrInit1DayFailedFullInits     Unsigned32,
      adsl2PMLCurrInit1DayShortInits          Unsigned32,
      adsl2PMLCurrInit1DayFailedShortInits    Unsigned32
   }

adsl2PMLCurrInit15MTimeElapsed  OBJECT-TYPE
   SYNTAX      Unsigned32
   UNITS       "seconds"
   MAX-ACCESS  read-only
   STATUS      current
   DESCRIPTION
      "Total elapsed seconds since this PM interval began.
       Note that the PM counters are not reset even when the XTU
       is reinitialized.  They are reinitialized only when the
       agent itself is reset or reinitialized."
   ::= { adsl2PMLineCurrInitEntry 1 }

adsl2PMLCurrInit15MFullInits  OBJECT-TYPE
   SYNTAX      Unsigned32
   MAX-ACCESS  read-only
   STATUS      current
   DESCRIPTION
      "Count of full initializations attempted on the line
       (successful and failed) during this interval."
   REFERENCE    "ITU-T G.997.1, paragraph 7.2.1"
   ::= { adsl2PMLineCurrInitEntry 2 }

adsl2PMLCurrInit15MFailedFullInits  OBJECT-TYPE
   SYNTAX      Unsigned32
   MAX-ACCESS  read-only
   STATUS      current



   DESCRIPTION
      "Count of failed full initializations on the line during this
       interval."
   REFERENCE    "ITU-T G.997.1, paragraph 7.2.1"
   ::= { adsl2PMLineCurrInitEntry 3 }

adsl2PMLCurrInit15MShortInits  OBJECT-TYPE
   SYNTAX      Unsigned32
   MAX-ACCESS  read-only
   STATUS      current
   DESCRIPTION
      "Count of short initializations attempted on the line
       (successful and failed) during this interval."
   REFERENCE    "ITU-T G.997.1, paragraph 7.2.1"
   ::= { adsl2PMLineCurrInitEntry 4 }

adsl2PMLCurrInit15MFailedShortInits  OBJECT-TYPE
   SYNTAX      Unsigned32
   MAX-ACCESS  read-only
   STATUS      current
   DESCRIPTION
      "Count of failed short initializations on the line during this
       interval."
   REFERENCE    "ITU-T G.997.1, paragraph 7.2.1"
   ::= { adsl2PMLineCurrInitEntry 5 }

adsl2PMLCurrInit1DayTimeElapsed  OBJECT-TYPE
   SYNTAX      Unsigned32
   UNITS       "seconds"
   MAX-ACCESS  read-only
   STATUS      current
   DESCRIPTION
      "Total elapsed seconds since this PM interval began.
       Note that the PM counters are not reset even when the XTU
       is reinitialized.  They are reinitialized only when the
       agent itself is reset or reinitialized."
   ::= { adsl2PMLineCurrInitEntry 6 }

adsl2PMLCurrInit1DayFullInits  OBJECT-TYPE
   SYNTAX      Unsigned32
   MAX-ACCESS  read-only
   STATUS      current
   DESCRIPTION
      "Count of full initializations attempted on the line
       (successful and failed) during this interval."
   REFERENCE    "ITU-T G.997.1, paragraph 7.2.1"
   ::= { adsl2PMLineCurrInitEntry 7 }




adsl2PMLCurrInit1DayFailedFullInits  OBJECT-TYPE
   SYNTAX      Unsigned32
   MAX-ACCESS  read-only
   STATUS      current
   DESCRIPTION
      "Count of failed full initializations on the line during this
       interval."
   REFERENCE    "ITU-T G.997.1, paragraph 7.2.1"
   ::= { adsl2PMLineCurrInitEntry 8 }

adsl2PMLCurrInit1DayShortInits  OBJECT-TYPE
   SYNTAX      Unsigned32
   MAX-ACCESS  read-only
   STATUS      current
   DESCRIPTION
      "Count of short initializations attempted on the line
       (successful and failed) during this interval."
   REFERENCE    "ITU-T G.997.1, paragraph 7.2.1"
   ::= { adsl2PMLineCurrInitEntry 9 }

adsl2PMLCurrInit1DayFailedShortInits  OBJECT-TYPE
   SYNTAX      Unsigned32
   MAX-ACCESS  read-only
   STATUS      current
   DESCRIPTION
      "Count of failed short initializations on the line during this
       interval."
   REFERENCE    "ITU-T G.997.1, paragraph 7.2.1"
   ::= { adsl2PMLineCurrInitEntry 10 }



-------------------------------------------
--       PM line history 15 Minutes      --
-------------------------------------------
adsl2PMLineHist15MinTable    OBJECT-TYPE
   SYNTAX      SEQUENCE  OF  Adsl2PMLineHist15MinEntry
   MAX-ACCESS  not-accessible
   STATUS      current
   DESCRIPTION
      "The table adsl2PMLineHist15MinTable contains PM line history
      for 15min intervals of the ADSL2 line."
   ::= { adsl2PMLine 3 }

adsl2PMLineHist15MinEntry  OBJECT-TYPE
   SYNTAX      Adsl2PMLineHist15MinEntry
   MAX-ACCESS  not-accessible
   STATUS      current



   DESCRIPTION
      "The table adsl2PMLineHist15MinTable contains PM line history
       for 15min intervals of the ADSL2 line.
       The index of this table consists of an interface index, where
       the interface has an ifType of adsl2plus(238), along with a
       termination unit, and an interval number."
   INDEX  { ifIndex,
            adsl2PMLHist15MUnit,
            adsl2PMLHist15MInterval }
   ::= { adsl2PMLineHist15MinTable 1 }

Adsl2PMLineHist15MinEntry  ::=
   SEQUENCE {
      adsl2PMLHist15MUnit                 Adsl2Unit,
      adsl2PMLHist15MInterval             Unsigned32,
      adsl2PMLHist15MMonitoredTime        Unsigned32,
      adsl2PMLHist15MFecs                 Counter32,
      adsl2PMLHist15MEs                   Counter32,
      adsl2PMLHist15MSes                  Counter32,
      adsl2PMLHist15MLoss                 Counter32,
      adsl2PMLHist15MUas                  Counter32,
      adsl2PMLHist15MValidInterval        TruthValue
   }

adsl2PMLHist15MUnit  OBJECT-TYPE
   SYNTAX      Adsl2Unit
   MAX-ACCESS  not-accessible
   STATUS      current
   DESCRIPTION
      "The termination unit atuc(1) or atur(2)."
   ::= { adsl2PMLineHist15MinEntry 1 }

adsl2PMLHist15MInterval  OBJECT-TYPE
   SYNTAX      Unsigned32 (1..96)
   MAX-ACCESS  not-accessible
   STATUS      current
   DESCRIPTION
      "The interval number."
   ::= { adsl2PMLineHist15MinEntry 2 }

adsl2PMLHist15MMonitoredTime  OBJECT-TYPE
   SYNTAX      Unsigned32
   UNITS       "seconds"
   MAX-ACCESS  read-only
   STATUS      current
   DESCRIPTION
      "Total seconds monitored in this interval."
   ::= { adsl2PMLineHist15MinEntry 3 }



adsl2PMLHist15MFecs  OBJECT-TYPE
   SYNTAX      Counter32
   UNITS       "seconds"
   MAX-ACCESS  read-only
   STATUS      current
   DESCRIPTION
      "Count of seconds during this interval where there was at least
       one FEC correction event for one or more bearer channels in
       this line.  This parameter is inhibited during UAS or SES."
   REFERENCE    "ITU-T G.997.1, paragraph 7.2.1"
   ::= { adsl2PMLineHist15MinEntry 4 }

adsl2PMLHist15MEs  OBJECT-TYPE
   SYNTAX      Counter32
   UNITS       "seconds"
   MAX-ACCESS  read-only
   STATUS      current
   DESCRIPTION
      "Count of seconds during this interval where there was:
          ATU-C: CRC-8 >= 1 for one or more bearer channels OR
                 LOS >= 1 OR SEF >= 1 OR LPR >= 1
          ATU-R: FEBE >= 1 for one or more bearer channels OR
                 LOS-FE >= 1 OR RDI >= 1 OR LPR-FE >= 1.
       This parameter is inhibited during UAS."
   REFERENCE    "ITU-T G.997.1, paragraph 7.2.1"
   ::= { adsl2PMLineHist15MinEntry 5 }

adsl2PMLHist15MSes  OBJECT-TYPE
   SYNTAX      Counter32
   UNITS       "seconds"
   MAX-ACCESS  read-only
   STATUS      current
   DESCRIPTION
      "Count of seconds during this interval where there was:
          ATU-C: (CRC-8 summed over all bearer channels) >= 18 OR
                 LOS >= 1 OR SEF >= 1 OR LPR >= 1
          ATU-R: (FEBE summed over all bearer channels) >= 18 OR
                 LOS-FE >= 1 OR RDI >= 1 OR LPR-FE >= 1.
       This parameter is inhibited during UAS."
   REFERENCE    "ITU-T G.997.1, paragraph 7.2.1"
   ::= { adsl2PMLineHist15MinEntry 6 }

adsl2PMLHist15MLoss  OBJECT-TYPE
   SYNTAX      Counter32
   UNITS       "seconds"
   MAX-ACCESS  read-only
   STATUS      current
   DESCRIPTION



      "Count of seconds during this interval where there was LOS (or
       LOS-FE for ATU-R)."
   REFERENCE    "ITU-T G.997.1, paragraph 7.2.1"
   ::= { adsl2PMLineHist15MinEntry 7 }

adsl2PMLHist15MUas  OBJECT-TYPE
   SYNTAX      Counter32
   UNITS       "seconds"
   MAX-ACCESS  read-only
   STATUS      current
   DESCRIPTION
      "Count of seconds in Unavailability State during this interval.
       Unavailability begins at the onset of 10 contiguous severely-
       errored seconds, and ends at the onset of 10 contiguous
       seconds with no severely-errored seconds."
   REFERENCE    "ITU-T G.997.1, paragraph 7.2.1"
   ::= { adsl2PMLineHist15MinEntry 8 }

adsl2PMLHist15MValidInterval  OBJECT-TYPE
   SYNTAX      TruthValue
   MAX-ACCESS  read-only
   STATUS      current
   DESCRIPTION
      "This variable indicates if the data for this interval is
       valid."
   ::= { adsl2PMLineHist15MinEntry 9 }



---------------------------------------
--       PM line history 1 Day       --
---------------------------------------
adsl2PMLineHist1DayTable     OBJECT-TYPE
   SYNTAX      SEQUENCE  OF  Adsl2PMLineHist1DayEntry
   MAX-ACCESS  not-accessible
   STATUS      current
   DESCRIPTION
      "The table adsl2PMLineHist1DayTable contains PM line history
       for 24-hour intervals of the ADSL2 line."
   ::= { adsl2PMLine 4 }

adsl2PMLineHist1DayEntry  OBJECT-TYPE
   SYNTAX      Adsl2PMLineHist1DayEntry
   MAX-ACCESS  not-accessible
   STATUS      current
   DESCRIPTION
      "The table adsl2PMLineHist1DayTable contains PM line history
       for 24-hour intervals of the ADSL2 line.



       The index of this table consists of an interface index, where
       the interface has an ifType of adsl2plus(238), along with a
       termination unit, and an interval number."
   INDEX  { ifIndex,
            adsl2PMLHist1DUnit,
            adsl2PMLHist1DInterval }
   ::= { adsl2PMLineHist1DayTable 1 }

Adsl2PMLineHist1DayEntry  ::=
   SEQUENCE {
      adsl2PMLHist1DUnit              Adsl2Unit,
      adsl2PMLHist1DInterval          Unsigned32,
      adsl2PMLHist1DMonitoredTime     Unsigned32,
      adsl2PMLHist1DFecs              Counter32,
      adsl2PMLHist1DEs                Counter32,
      adsl2PMLHist1DSes               Counter32,
      adsl2PMLHist1DLoss              Counter32,
      adsl2PMLHist1DUas               Counter32,
      adsl2PMLHist1DValidInterval     TruthValue
   }

adsl2PMLHist1DUnit  OBJECT-TYPE
   SYNTAX      Adsl2Unit
   MAX-ACCESS  not-accessible
   STATUS      current
   DESCRIPTION
      "The termination unit."
   ::= { adsl2PMLineHist1DayEntry 1 }

adsl2PMLHist1DInterval  OBJECT-TYPE
   SYNTAX      Unsigned32 (1..30)
   MAX-ACCESS  not-accessible
   STATUS      current
   DESCRIPTION
      "The interval number."
   ::= { adsl2PMLineHist1DayEntry 2 }

adsl2PMLHist1DMonitoredTime  OBJECT-TYPE
   SYNTAX      Unsigned32
   UNITS       "seconds"
   MAX-ACCESS  read-only
   STATUS      current
   DESCRIPTION
      "Total seconds monitored in this interval."
   ::= { adsl2PMLineHist1DayEntry 3 }

adsl2PMLHist1DFecs  OBJECT-TYPE
   SYNTAX      Counter32



   UNITS       "seconds"
   MAX-ACCESS  read-only
   STATUS      current
   DESCRIPTION
      "Count of seconds during this interval where there was at least
       one FEC correction event for one or more bearer channels in
       this line.  This parameter is inhibited during UAS or SES."
   REFERENCE    "ITU-T G.997.1, paragraph 7.2.1"
   ::= { adsl2PMLineHist1DayEntry 4 }

adsl2PMLHist1DEs  OBJECT-TYPE
   SYNTAX      Counter32
   UNITS       "seconds"
   MAX-ACCESS  read-only
   STATUS      current
   DESCRIPTION
      "Count of seconds during this interval where there was:
          ATU-C: CRC-8 >= 1 for one or more bearer channels OR
                 LOS >= 1 OR SEF >= 1 OR LPR >= 1
          ATU-R: FEBE >= 1 for one or more bearer channels OR
                 LOS-FE >= 1 OR RDI >= 1 OR LPR-FE >= 1.
       This parameter is inhibited during UAS."
   REFERENCE    "ITU-T G.997.1, paragraph 7.2.1"
   ::= { adsl2PMLineHist1DayEntry 5 }

adsl2PMLHist1DSes  OBJECT-TYPE
   SYNTAX      Counter32
   UNITS       "seconds"
   MAX-ACCESS  read-only
   STATUS      current
   DESCRIPTION
      "Count of seconds during this interval where there was:
          ATU-C: (CRC-8 summed over all bearer channels) >= 18 OR
                  LOS >= 1 OR SEF >> 1 OR LPR >= 1
          ATU-R: (FEBE summed over all bearer channels) >= 18 OR
                  LOS-FE >= 1 OR RDI >= 1 OR LPR-FE >= 1.
       This parameter is inhibited during UAS."
   REFERENCE    "ITU-T G.997.1, paragraph 7.2.1"
   ::= { adsl2PMLineHist1DayEntry 6 }

adsl2PMLHist1DLoss  OBJECT-TYPE
   SYNTAX      Counter32
   UNITS       "seconds"
   MAX-ACCESS  read-only
   STATUS      current
   DESCRIPTION
      "Count of seconds during this interval where there was LOS (or
       LOS-FE for ATU-R)."



   REFERENCE    "ITU-T G.997.1, paragraph 7.2.1"
   ::= { adsl2PMLineHist1DayEntry 7 }

adsl2PMLHist1DUas  OBJECT-TYPE
   SYNTAX      Counter32
   UNITS       "seconds"
   MAX-ACCESS  read-only
   STATUS      current
   DESCRIPTION
      "Count of seconds in Unavailability State during this interval.
       Unavailability begins at the onset of 10 contiguous severely-
       errored seconds, and ends at the onset of 10 contiguous
       seconds with no severely-errored seconds."
   REFERENCE    "ITU-T G.997.1, paragraph 7.2.1"
   ::= { adsl2PMLineHist1DayEntry 8 }

adsl2PMLHist1DValidInterval  OBJECT-TYPE
   SYNTAX      TruthValue
   MAX-ACCESS  read-only
   STATUS      current
   DESCRIPTION
      "This variable indicates if the data for this interval is
       valid."
   ::= { adsl2PMLineHist1DayEntry 9 }




-------------------------------------------
--     PM line init history 15 Minutes   --
-------------------------------------------

adsl2PMLineInitHist15MinTable      OBJECT-TYPE
   SYNTAX      SEQUENCE  OF  Adsl2PMLineInitHist15MinEntry
   MAX-ACCESS  not-accessible
   STATUS      current
   DESCRIPTION
      "The table adsl2PMLineInitHist15MinTable contains PM line
       initialization history for 15-minute intervals of the ADSL2
       line."
   ::= { adsl2PMLine 5 }

adsl2PMLineInitHist15MinEntry  OBJECT-TYPE
   SYNTAX      Adsl2PMLineInitHist15MinEntry
   MAX-ACCESS  not-accessible
   STATUS      current
   DESCRIPTION
      "The table adsl2PMLineInitHist15MinTable contains PM line



       initialization history for 15 minutes intervals of the ADSL2
       line.
       The index of this table consists of an interface index, where
       the interface has an ifType of adsl2plus(238), and an interval
       number."
   INDEX  { ifIndex,
            adsl2PMLHistInit15MInterval }
   ::= { adsl2PMLineInitHist15MinTable 1 }

Adsl2PMLineInitHist15MinEntry  ::=
   SEQUENCE {
      adsl2PMLHistInit15MInterval              Unsigned32,
      adsl2PMLHistInit15MMonitoredTime         Unsigned32,
      adsl2PMLHistInit15MFullInits             Unsigned32,
      adsl2PMLHistInit15MFailedFullInits       Unsigned32,
      adsl2PMLHistInit15MShortInits            Unsigned32,
      adsl2PMLHistInit15MFailedShortInits      Unsigned32,
      adsl2PMLHistInit15MValidInterval         TruthValue
   }

adsl2PMLHistInit15MInterval  OBJECT-TYPE
   SYNTAX      Unsigned32 (1..96)
   MAX-ACCESS  not-accessible
   STATUS      current
   DESCRIPTION
      "The interval number."
   ::= { adsl2PMLineInitHist15MinEntry 1 }

adsl2PMLHistInit15MMonitoredTime  OBJECT-TYPE
   SYNTAX      Unsigned32
   UNITS       "seconds"
   MAX-ACCESS  read-only
   STATUS      current
   DESCRIPTION
      "Total seconds monitored in this interval."
   ::= { adsl2PMLineInitHist15MinEntry 2 }

adsl2PMLHistInit15MFullInits  OBJECT-TYPE
   SYNTAX      Unsigned32
   MAX-ACCESS  read-only
   STATUS      current
   DESCRIPTION
      "Count of full initializations attempted on the line
       (successful and failed) during this interval."
   REFERENCE    "ITU-T G.997.1, paragraph 7.2.1"
   ::= { adsl2PMLineInitHist15MinEntry 3 }

adsl2PMLHistInit15MFailedFullInits  OBJECT-TYPE



   SYNTAX      Unsigned32
   MAX-ACCESS  read-only
   STATUS      current
   DESCRIPTION
      "Count of failed full initializations on the line during this
       interval."
   REFERENCE    "ITU-T G.997.1, paragraph 7.2.1"
   ::= { adsl2PMLineInitHist15MinEntry 4 }

adsl2PMLHistInit15MShortInits  OBJECT-TYPE
   SYNTAX      Unsigned32
   MAX-ACCESS  read-only
   STATUS      current
   DESCRIPTION
      "Count of short initializations attempted on the line
       (successful and failed) during this interval."
   REFERENCE    "ITU-T G.997.1, paragraph 7.2.1"
   ::= { adsl2PMLineInitHist15MinEntry 5 }

adsl2PMLHistInit15MFailedShortInits  OBJECT-TYPE
   SYNTAX      Unsigned32
   MAX-ACCESS  read-only
   STATUS      current
   DESCRIPTION
      "Count of failed short initializations on the line during this
       interval."
   REFERENCE    "ITU-T G.997.1, paragraph 7.2.1"
   ::= { adsl2PMLineInitHist15MinEntry 6 }

adsl2PMLHistInit15MValidInterval  OBJECT-TYPE
   SYNTAX      TruthValue
   MAX-ACCESS  read-only
   STATUS      current
   DESCRIPTION
      "This variable indicates if the data for this interval is
       valid."
   ::= { adsl2PMLineInitHist15MinEntry 7 }



-------------------------------------------
--       PM line init history 1 Day      --
-------------------------------------------
adsl2PMLineInitHist1DayTable       OBJECT-TYPE
   SYNTAX      SEQUENCE  OF  Adsl2PMLineInitHist1DayEntry
   MAX-ACCESS  not-accessible
   STATUS      current
   DESCRIPTION



      "The table adsl2PMLineInitHist1DayTable contains PM line
       initialization history for 24-hour intervals of the ADSL2
       line."
   ::= { adsl2PMLine 6 }

adsl2PMLineInitHist1DayEntry  OBJECT-TYPE
   SYNTAX      Adsl2PMLineInitHist1DayEntry
   MAX-ACCESS  not-accessible
   STATUS      current
   DESCRIPTION
      "The table adsl2PMLineInitHist1DayTable contains PM line
       initialization history for 24-hour intervals of the ADSL2
       line.
       The index of this table consists of an interface index, where
       the interface has an ifType of adsl2plus(238), and an interval
       number."
   INDEX  { ifIndex,
            adsl2PMLHistinit1DInterval }
   ::= { adsl2PMLineInitHist1DayTable 1 }

Adsl2PMLineInitHist1DayEntry  ::=
   SEQUENCE {
      adsl2PMLHistinit1DInterval              Unsigned32,
      adsl2PMLHistinit1DMonitoredTime         Unsigned32,
      adsl2PMLHistinit1DFullInits             Unsigned32,
      adsl2PMLHistinit1DFailedFullInits       Unsigned32,
      adsl2PMLHistinit1DShortInits            Unsigned32,
      adsl2PMLHistinit1DFailedShortInits      Unsigned32,
      adsl2PMLHistinit1DValidInterval         TruthValue
   }

adsl2PMLHistinit1DInterval  OBJECT-TYPE
   SYNTAX      Unsigned32 (1..30)
   MAX-ACCESS  not-accessible
   STATUS      current
   DESCRIPTION
      "The interval number."
   ::= { adsl2PMLineInitHist1DayEntry 1 }

adsl2PMLHistinit1DMonitoredTime  OBJECT-TYPE
   SYNTAX      Unsigned32
   UNITS       "seconds"
   MAX-ACCESS  read-only
   STATUS      current
   DESCRIPTION
      "Total seconds monitored in this interval."
   ::= { adsl2PMLineInitHist1DayEntry 2 }




adsl2PMLHistinit1DFullInits  OBJECT-TYPE
   SYNTAX      Unsigned32
   MAX-ACCESS  read-only
   STATUS      current
   DESCRIPTION
      "Count of full initializations attempted on the line
       (successful and failed) during this interval."
   REFERENCE    "ITU-T G.997.1, paragraph 7.2.1"
    ::= { adsl2PMLineInitHist1DayEntry 3 }

adsl2PMLHistinit1DFailedFullInits  OBJECT-TYPE
   SYNTAX      Unsigned32
   MAX-ACCESS  read-only
   STATUS      current
   DESCRIPTION
      "Count of failed full initializations on the line during this
       interval."
   REFERENCE    "ITU-T G.997.1, paragraph 7.2.1"
   ::= { adsl2PMLineInitHist1DayEntry 4 }

adsl2PMLHistinit1DShortInits  OBJECT-TYPE
   SYNTAX      Unsigned32
   MAX-ACCESS  read-only
   STATUS      current
   DESCRIPTION
      "Count of short initializations attempted on the line
       (successful and failed) during this interval."
   REFERENCE    "ITU-T G.997.1, paragraph 7.2.1"
   ::= { adsl2PMLineInitHist1DayEntry 5 }

adsl2PMLHistinit1DFailedShortInits  OBJECT-TYPE
   SYNTAX      Unsigned32
   MAX-ACCESS  read-only
   STATUS      current
   DESCRIPTION
      "Count of failed short initializations on the line during this
       interval."
   REFERENCE    "ITU-T G.997.1, paragraph 7.2.1"
   ::= { adsl2PMLineInitHist1DayEntry 6 }

adsl2PMLHistinit1DValidInterval  OBJECT-TYPE
   SYNTAX      TruthValue
   MAX-ACCESS  read-only
   STATUS      current
   DESCRIPTION
      "This variable indicates if the data for this interval is
       valid."
   ::= { adsl2PMLineInitHist1DayEntry 7 }



---------------------------------------------------
--          PM channel current counters          --
---------------------------------------------------
adsl2PMChCurrTable        OBJECT-TYPE
   SYNTAX      SEQUENCE  OF  Adsl2PMChCurrEntry
   MAX-ACCESS  not-accessible
   STATUS      current
   DESCRIPTION
      "The table adsl2PMChCurrTable contains current Performance
       Monitoring results of the ADSL2 channel.
       The PM counters in the table are not reset even when the XTU
       is reinitialized. They are reinitialized only when the
       agent itself is reset or reinitialized."
   ::= { adsl2PMChannel 1 }

adsl2PMChCurrEntry  OBJECT-TYPE
   SYNTAX      Adsl2PMChCurrEntry
   MAX-ACCESS  not-accessible
   STATUS      current
   DESCRIPTION
      "The table adsl2PMChCurrTable contains current Performance
       Monitoring results of the ADSL2 channel.
       The index of this table consists of an interface index, where
       the interface has an ifType value that is applicable
       for a DSL channel, along with a termination unit."
   INDEX  { ifIndex, adsl2PMChCurrUnit }
   ::= { adsl2PMChCurrTable 1 }

Adsl2PMChCurrEntry  ::=
   SEQUENCE {
      adsl2PMChCurrUnit                     Adsl2Unit,
      adsl2PMChCurrValidIntervals           Unsigned32,
      adsl2PMChCurrInvalidIntervals         Unsigned32,
      adsl2PMChCurr15MTimeElapsed           HCPerfTimeElapsed,
      adsl2PMChCurr15MCodingViolations      Unsigned32,
      adsl2PMChCurr15MCorrectedBlocks       Unsigned32,
      adsl2PMChCurr1DayValidIntervals       Unsigned32,
      adsl2PMChCurr1DayInvalidIntervals     Unsigned32,
      adsl2PMChCurr1DayTimeElapsed          HCPerfTimeElapsed,
      adsl2PMChCurr1DayCodingViolations     Unsigned32,
      adsl2PMChCurr1DayCorrectedBlocks      Unsigned32
   }

adsl2PMChCurrUnit  OBJECT-TYPE
   SYNTAX      Adsl2Unit
   MAX-ACCESS  not-accessible
   STATUS      current
   DESCRIPTION



   "The termination unit."
   ::= { adsl2PMChCurrEntry 1 }

adsl2PMChCurrValidIntervals  OBJECT-TYPE
   SYNTAX      Unsigned32
   MAX-ACCESS  read-only
   STATUS      current
   DESCRIPTION
      "Valid intervals."
   ::= { adsl2PMChCurrEntry 2 }

adsl2PMChCurrInvalidIntervals  OBJECT-TYPE
   SYNTAX      Unsigned32
   MAX-ACCESS  read-only
   STATUS      current
   DESCRIPTION
      "Invalid intervals."
    ::= { adsl2PMChCurrEntry 3 }

adsl2PMChCurr15MTimeElapsed  OBJECT-TYPE
   SYNTAX      HCPerfTimeElapsed
   UNITS       "seconds"
   MAX-ACCESS  read-only
   STATUS      current
   DESCRIPTION
      "Total elapsed seconds since this PM interval began.
       Note that the PM counters are not reset even when the XTU
       is reinitialized. They are reinitialized only when the
       agent itself is reset or reinitialized."
   ::= { adsl2PMChCurrEntry 4 }

adsl2PMChCurr15MCodingViolations  OBJECT-TYPE
   SYNTAX      Unsigned32
   MAX-ACCESS  read-only
   STATUS      current
   DESCRIPTION
      "Count of CRC-8 (FEBE for ATU-R) anomalies occurring in the
       channel during the interval.  This parameter is inhibited
       during UAS or SES.  If the CRC is applied over multiple
       channels, then each related CRC-8 (or FEBE) anomaly should
       increment each of the counters related to the individual
       channels."
   REFERENCE    "ITU-T G.997.1, paragraph 7.2.2"
  ::= { adsl2PMChCurrEntry 5 }

adsl2PMChCurr15MCorrectedBlocks  OBJECT-TYPE
   SYNTAX      Unsigned32
   MAX-ACCESS  read-only



   STATUS      current
   DESCRIPTION
      "Count of FEC (FFEC for ATU-R) anomalies (corrected code words)
       occurring in the channel during the interval.  This parameter
       is inhibited during UAS or SES.  If the FEC is applied over
       multiple channels, then each related FEC (or FFEC) anomaly
       should increment each of the counters related to the
       individual channels."
   REFERENCE    "ITU-T G.997.1, paragraph 7.2.2"
   ::= { adsl2PMChCurrEntry 6 }

adsl2PMChCurr1DayValidIntervals  OBJECT-TYPE
   SYNTAX      Unsigned32
   MAX-ACCESS  read-only
   STATUS      current
   DESCRIPTION
      "Valid intervals."
   ::= { adsl2PMChCurrEntry 7 }

adsl2PMChCurr1DayInvalidIntervals  OBJECT-TYPE
   SYNTAX      Unsigned32
   MAX-ACCESS  read-only
   STATUS      current
   DESCRIPTION
      "Invalid intervals."
   ::= { adsl2PMChCurrEntry 8 }

adsl2PMChCurr1DayTimeElapsed  OBJECT-TYPE
   SYNTAX      HCPerfTimeElapsed
   UNITS       "seconds"
   MAX-ACCESS  read-only
   STATUS      current
   DESCRIPTION
      "Total elapsed seconds since this PM interval began.
       Note that the PM counters are not reset even when the XTU
       is reinitialized. They are reinitialized only when the
       agent itself is reset or reinitialized."
   ::= { adsl2PMChCurrEntry 9 }

adsl2PMChCurr1DayCodingViolations  OBJECT-TYPE
   SYNTAX      Unsigned32
   MAX-ACCESS  read-only
   STATUS      current
   DESCRIPTION
      "Count of CRC-8 (FEBE for ATU-R) anomalies occurring in the
       channel during the interval.  This parameter is inhibited
       during UAS or SES.  If the CRC is applied over multiple
       channels, then each related CRC-8 (or FEBE) anomaly should



       increment each of the counters related to the individual
       channels."
   REFERENCE    "ITU-T G.997.1, paragraph 7.2.2"
   ::= { adsl2PMChCurrEntry 10 }

adsl2PMChCurr1DayCorrectedBlocks  OBJECT-TYPE
   SYNTAX      Unsigned32
   MAX-ACCESS  read-only
   STATUS      current
   DESCRIPTION
      "Count of FEC (FFEC for ATU-R) anomalies (corrected code words)
       occurring in the channel during the interval.  This parameter
       is inhibited during UAS or SES.  If the FEC is applied over
       multiple channels, then each related FEC (or FFEC) anomaly
       should increment each of the counters related to the
       individual channels."
   REFERENCE    "ITU-T G.997.1, paragraph 7.2.2"
   ::= { adsl2PMChCurrEntry 11 }



-------------------------------------------
--    PM channel history 15 Minutes      --
-------------------------------------------
adsl2PMChHist15MinTable         OBJECT-TYPE
   SYNTAX      SEQUENCE  OF  Adsl2PMChHist15MinEntry
   MAX-ACCESS  not-accessible
   STATUS      current
   DESCRIPTION
      "The table adsl2PMChCurrTable contains current Performance
       Monitoring results of the ADSL2 channel."
   ::= { adsl2PMChannel 2 }

adsl2PMChHist15MinEntry  OBJECT-TYPE
   SYNTAX      Adsl2PMChHist15MinEntry
   MAX-ACCESS  not-accessible
   STATUS      current
   DESCRIPTION
      "The table adsl2PMChCurrTable contains current Performance
       Monitoring results of the ADSL2 channel.
       The index of this table consists of an interface index, where
       the interface has an ifType value that is applicable
       for a DSL channel, along with a termination unit, and the
       interval number."
   INDEX  { ifIndex,
            adsl2PMChHist15MUnit,
            adsl2PMChHist15MInterval }
   ::= { adsl2PMChHist15MinTable 1 }



Adsl2PMChHist15MinEntry  ::=
   SEQUENCE {
      adsl2PMChHist15MUnit                     Adsl2Unit,
      adsl2PMChHist15MInterval                 Unsigned32,
      adsl2PMChHist15MMonitoredTime            Unsigned32,
      adsl2PMChHist15MCodingViolations         Unsigned32,
      adsl2PMChHist15MCorrectedBlocks          Unsigned32,
      adsl2PMChHist15MValidInterval            TruthValue
   }

adsl2PMChHist15MUnit  OBJECT-TYPE
   SYNTAX      Adsl2Unit
   MAX-ACCESS  not-accessible
   STATUS      current
   DESCRIPTION
      "The termination unit."
   ::= { adsl2PMChHist15MinEntry 1 }

adsl2PMChHist15MInterval  OBJECT-TYPE
   SYNTAX      Unsigned32 (1..96)
   MAX-ACCESS  not-accessible
   STATUS      current
   DESCRIPTION
      "The interval number."
   ::= { adsl2PMChHist15MinEntry 2 }

adsl2PMChHist15MMonitoredTime  OBJECT-TYPE
   SYNTAX      Unsigned32
   UNITS       "seconds"
   MAX-ACCESS  read-only
   STATUS      current
   DESCRIPTION
      "Total seconds monitored in this interval."
   ::= { adsl2PMChHist15MinEntry 3 }

adsl2PMChHist15MCodingViolations  OBJECT-TYPE
   SYNTAX      Unsigned32
   MAX-ACCESS  read-only
   STATUS      current
   DESCRIPTION
      "Count of CRC-8 (FEBE for ATU-R) anomalies occurring in the
       channel during the interval.  This parameter is inhibited
       during UAS or SES.  If the CRC is applied over multiple
       channels, then each related CRC-8 (or FEBE) anomaly should
       increment each of the counters related to the individual
       channels."
   REFERENCE    "ITU-T G.997.1, paragraph 7.2.2"
   ::= { adsl2PMChHist15MinEntry 4 }



adsl2PMChHist15MCorrectedBlocks  OBJECT-TYPE
   SYNTAX      Unsigned32
   MAX-ACCESS  read-only
   STATUS      current
   DESCRIPTION
      "Count of FEC (FFEC for ATU-R) anomalies (corrected code words)
       occurring in the channel during the interval.  This parameter
       is inhibited during UAS or SES.  If the FEC is applied over
       multiple channels, then each related FEC (or FFEC) anomaly
       should increment each of the counters related to the
       individual channels."
   REFERENCE    "ITU-T G.997.1, paragraph 7.2.2"
   ::= { adsl2PMChHist15MinEntry 5 }

adsl2PMChHist15MValidInterval  OBJECT-TYPE
   SYNTAX      TruthValue
   MAX-ACCESS  read-only
   STATUS      current
   DESCRIPTION
      "This variable indicates if the data for this interval is
       valid."
   ::= { adsl2PMChHist15MinEntry 6 }



------------------------------------------
--        PM channel history 1 Day      --
------------------------------------------
adsl2PMChHist1DTable         OBJECT-TYPE
   SYNTAX      SEQUENCE  OF  Adsl2PMChHist1DEntry
   MAX-ACCESS  not-accessible
   STATUS      current
   DESCRIPTION
      "The table adsl2PMChHist1DayTable contains PM channel history
       for 1-day intervals of ADSL2."
   ::= { adsl2PMChannel 3 }

adsl2PMChHist1DEntry  OBJECT-TYPE
   SYNTAX      Adsl2PMChHist1DEntry
   MAX-ACCESS  not-accessible
   STATUS      current
   DESCRIPTION
      "The table adsl2PMChHist1DayTable contains PM channel history
       for 1-day intervals of ADSL2.
       The index of this table consists of an interface index, where
       the interface has an ifType value that is applicable
       for a DSL channel, along with a termination unit, and the
       interval number."



   INDEX  { ifIndex,
            adsl2PMChHist1DUnit,
            adsl2PMChHist1DInterval }
   ::= { adsl2PMChHist1DTable 1 }

Adsl2PMChHist1DEntry  ::=
   SEQUENCE {
      adsl2PMChHist1DUnit                      Adsl2Unit,
      adsl2PMChHist1DInterval                  Unsigned32,
      adsl2PMChHist1DMonitoredTime             Unsigned32,
      adsl2PMChHist1DCodingViolations          Unsigned32,
      adsl2PMChHist1DCorrectedBlocks           Unsigned32,
      adsl2PMChHist1DValidInterval             TruthValue
   }

adsl2PMChHist1DUnit  OBJECT-TYPE
   SYNTAX      Adsl2Unit
   MAX-ACCESS  not-accessible
   STATUS      current
   DESCRIPTION
      "The termination unit."
    ::= { adsl2PMChHist1DEntry 1 }

adsl2PMChHist1DInterval  OBJECT-TYPE
   SYNTAX      Unsigned32 (1..30)
   MAX-ACCESS  not-accessible
   STATUS      current
   DESCRIPTION
      "The interval number."
   ::= { adsl2PMChHist1DEntry 2 }

adsl2PMChHist1DMonitoredTime  OBJECT-TYPE
   SYNTAX      Unsigned32
   UNITS       "seconds"
   MAX-ACCESS  read-only
   STATUS      current
   DESCRIPTION
      "Total seconds monitored in this interval."
   ::= { adsl2PMChHist1DEntry 3 }

adsl2PMChHist1DCodingViolations  OBJECT-TYPE
   SYNTAX      Unsigned32
   MAX-ACCESS  read-only
   STATUS      current
   DESCRIPTION
      "Count of CRC-8 (FEBE for ATU-R) anomalies occurring in the
       channel during the interval.  This parameter is inhibited
       during UAS or SES.  If the CRC is applied over multiple



       channels, then each related CRC-8 (or FEBE) anomaly should
       increment each of the counters related to the individual
       channels."
   REFERENCE    "ITU-T G.997.1, paragraph 7.2.2"
   ::= { adsl2PMChHist1DEntry 4 }

adsl2PMChHist1DCorrectedBlocks  OBJECT-TYPE
   SYNTAX      Unsigned32
   MAX-ACCESS  read-only
   STATUS      current
   DESCRIPTION
      "Count of FEC (FFEC for ATU-R) anomalies (corrected code words)
       occurring in the channel during the interval.  This parameter
       is inhibited during UAS or SES.  If the FEC is applied over
       multiple channels, then each related FEC (or FFEC) anomaly
       should increment each of the counters related to the
       individual channels."
   REFERENCE    "ITU-T G.997.1, paragraph 7.2.2"
   ::= { adsl2PMChHist1DEntry 5 }

adsl2PMChHist1DValidInterval  OBJECT-TYPE
   SYNTAX      TruthValue
   MAX-ACCESS  read-only
   STATUS      current
   DESCRIPTION
      "This variable indicates if the data for this interval is
       valid."
   ::= { adsl2PMChHist1DEntry 6 }

-------------------------------------------
--          Notifications Group          --
-------------------------------------------

adsl2LinePerfFECSThreshAtuc NOTIFICATION-TYPE
   OBJECTS
   {
   adsl2PMLCurr15MFecs,
   adsl2LineAlarmConfProfileAtucThresh15MinFecs
   }
   STATUS     current
   DESCRIPTION
     "This notification indicates that the FEC seconds threshold
      has been reached/exceeded for the referred ATU-C."
   ::= { adsl2Notifications 1 }

adsl2LinePerfFECSThreshAtur NOTIFICATION-TYPE
   OBJECTS
   {



   adsl2PMLCurr15MFecs,
   adsl2LineAlarmConfProfileAturThresh15MinFecs
   }
   STATUS     current
   DESCRIPTION
     "This notification indicates that the FEC seconds threshold
      has been reached/exceeded for the referred ATU-R."
   ::= { adsl2Notifications 2 }

adsl2LinePerfESThreshAtuc NOTIFICATION-TYPE
   OBJECTS
   {
   adsl2PMLCurr15MEs,
   adsl2LineAlarmConfProfileAtucThresh15MinEs
   }
   STATUS     current
   DESCRIPTION
     "This notification indicates that the errored seconds threshold
      has been reached/exceeded for the referred ATU-C."
   ::= { adsl2Notifications 3 }

adsl2LinePerfESThreshAtur NOTIFICATION-TYPE
   OBJECTS
   {
   adsl2PMLCurr15MEs,
   adsl2LineAlarmConfProfileAturThresh15MinEs
   }
   STATUS     current
   DESCRIPTION
     "This notification indicates that the errored seconds threshold
      has been reached/exceeded for the referred ATU-R."
   ::= { adsl2Notifications 4 }

adsl2LinePerfSESThreshAtuc NOTIFICATION-TYPE
   OBJECTS
   {
   adsl2PMLCurr15MSes,
   adsl2LineAlarmConfProfileAtucThresh15MinSes
   }
   STATUS     current
   DESCRIPTION
     "This notification indicates that the severely-errored seconds
      threshold has been reached/exceeded for the referred ATU-C."
   ::= { adsl2Notifications 5 }

adsl2LinePerfSESThreshAtur NOTIFICATION-TYPE
   OBJECTS
   {



   adsl2PMLCurr15MSes,
   adsl2LineAlarmConfProfileAturThresh15MinSes
   }
   STATUS     current
   DESCRIPTION
     "This notification indicates that the severely-errored seconds
      threshold has been reached/exceeded for the referred ATU-R."
   ::= { adsl2Notifications 6 }

adsl2LinePerfLOSSThreshAtuc NOTIFICATION-TYPE
   OBJECTS
   {
   adsl2PMLCurr15MLoss,
   adsl2LineAlarmConfProfileAtucThresh15MinLoss
   }
   STATUS     current
   DESCRIPTION
     "This notification indicates that the LOS seconds
      threshold has been reached/exceeded for the referred ATU-C."
   ::= { adsl2Notifications 7 }

adsl2LinePerfLOSSThreshAtur NOTIFICATION-TYPE
   OBJECTS
   {
   adsl2PMLCurr15MLoss,
   adsl2LineAlarmConfProfileAturThresh15MinLoss
   }
   STATUS     current
   DESCRIPTION
     "This notification indicates that the LOS seconds
      threshold has been reached/exceeded for the referred ATU-R."
   ::= { adsl2Notifications 8 }

adsl2LinePerfUASThreshAtuc NOTIFICATION-TYPE
   OBJECTS
   {
   adsl2PMLCurr15MUas,
   adsl2LineAlarmConfProfileAtucThresh15MinUas
   }
   STATUS     current
   DESCRIPTION
     "This notification indicates that the unavailable seconds
      threshold has been reached/exceeded for the referred ATU-C."
   ::= { adsl2Notifications 9 }

adsl2LinePerfUASThreshAtur NOTIFICATION-TYPE
   OBJECTS
   {



   adsl2PMLCurr15MUas,
   adsl2LineAlarmConfProfileAturThresh15MinUas
   }
   STATUS     current
   DESCRIPTION
     "This notification indicates that the unavailable seconds
      threshold has been reached/exceeded for the referred ATU-R."
   ::= { adsl2Notifications 10 }

adsl2LinePerfCodingViolationsThreshAtuc NOTIFICATION-TYPE
   OBJECTS
   {
   adsl2PMChCurr15MCodingViolations,
   adsl2ChAlarmConfProfileAtucThresh15MinCodingViolations
   }
   STATUS     current
   DESCRIPTION
     "This notification indicates that the coding violations
      threshold has been reached/exceeded for the referred ATU-C."
   ::= { adsl2Notifications 11 }

adsl2LinePerfCodingViolationsThreshAtur NOTIFICATION-TYPE
   OBJECTS
   {
   adsl2PMChCurr15MCodingViolations,
   adsl2ChAlarmConfProfileAturThresh15MinCodingViolations
   }
   STATUS     current
   DESCRIPTION
     "This notification indicates that the coding violations
      threshold has been reached/exceeded for the referred ATU-R."
   ::= { adsl2Notifications 12 }

adsl2LinePerfCorrectedThreshAtuc NOTIFICATION-TYPE
   OBJECTS
   {
   adsl2PMChCurr15MCorrectedBlocks,
   adsl2ChAlarmConfProfileAtucThresh15MinCorrected
   }
   STATUS     current
   DESCRIPTION
     "This notification indicates that the corrected blocks
      (FEC events) threshold has been reached/exceeded for the
      referred ATU-C."
   ::= { adsl2Notifications 13 }

adsl2LinePerfCorrectedThreshAtur NOTIFICATION-TYPE
   OBJECTS



   {
   adsl2PMChCurr15MCorrectedBlocks,
   adsl2ChAlarmConfProfileAturThresh15MinCorrected
   }
   STATUS     current
   DESCRIPTION
     "This notification indicates that the corrected blocks
      (FEC events) threshold has been reached/exceeded for the
      referred ATU-R."
   ::= { adsl2Notifications 14 }

adsl2LinePerfFailedFullInitThresh NOTIFICATION-TYPE
   OBJECTS
   {
   adsl2PMLCurrInit15MFailedFullInits,
   adsl2LineAlarmConfProfileThresh15MinFailedFullInt
   }
   STATUS     current
   DESCRIPTION
     "This notification indicates that the failed full
      initializations threshold has been reached/exceeded for the
      referred ADSL/ADSL2 or ADSL2+ line."
   ::= { adsl2Notifications 15 }

adsl2LinePerfFailedShortInitThresh NOTIFICATION-TYPE
   OBJECTS
   {
   adsl2PMLCurrInit15MFailedShortInits,
   adsl2LineAlarmConfProfileThresh15MinFailedShrtInt
   }
   STATUS     current
   DESCRIPTION
     "This notification indicates that the failed short
      initializations threshold has been reached/exceeded for the
      referred ADSL/ADSL2 or ADSL2+ line."
   ::= { adsl2Notifications 16 }

adsl2LineStatusChangeAtuc NOTIFICATION-TYPE
   OBJECTS
   {
   adsl2LineStatusAtuc
   }
   STATUS     current
   DESCRIPTION
     "This notification indicates that a status change is
      detected for the referred ATU-C."
   ::= { adsl2Notifications 17 }




adsl2LineStatusChangeAtur NOTIFICATION-TYPE
   OBJECTS
   {
   adsl2LineStatusAtur
   }
   STATUS     current
   DESCRIPTION
     "This notification indicates that a status change is
      detected for the referred ATU-R."
   ::= { adsl2Notifications 18 }


   -- conformance information

   adsl2Groups OBJECT IDENTIFIER ::= { adsl2Conformance 1 }
   adsl2Compliances OBJECT IDENTIFIER ::= { adsl2Conformance 2 }

   adsl2LineMibCompliance MODULE-COMPLIANCE
      STATUS  current
      DESCRIPTION
          "The compliance statement for SNMP entities that
          manage ADSL/ADSL2 or ADSL2+ interfaces."
      MODULE  -- this module
      MANDATORY-GROUPS
          {
          adsl2LineGroup,
          adsl2ChannelStatusGroup,
          adsl2SCStatusGroup,
          adsl2LineInventoryGroup,
          adsl2LineConfTemplateGroup,
          adsl2LineConfProfGroup,
          adsl2LineConfProfModeSpecGroup,
          adsl2ChConfProfileGroup,
          adsl2LineAlarmConfTemplateGroup,
          adsl2PMLineCurrGroup,
          adsl2PMLineCurrInitGroup,
          adsl2PMLineHist15MinGroup,
          adsl2PMLineHist1DayGroup,
          adsl2PMLineInitHist15MinGroup,
          adsl2PMLineInitHist1DayGroup,
          adsl2PMChCurrGroup,
          adsl2PMChHist15MinGroup,
          adsl2PMChHist1DGroup
          }

   GROUP  adsl2ChannelStatusAtmGroup
      DESCRIPTION
        "The group of status objects required when the data path



        is ATM."

   GROUP  adsl2ChannelStatusPtmGroup
      DESCRIPTION
        "The group of status objects required when the data path
        is PTM."

   GROUP  adsl2LineConfProfRaGroup
      DESCRIPTION
        "The group of objects required for controlling the rate-
        adaptive behavior of the line."

   GROUP  adsl2LineConfProfMsgMinGroup
      DESCRIPTION
        "The group of objects required for controlling the rate
        reserved for Overhead traffic."

   GROUP  adsl2LineAlarmConfProfileGroup
      DESCRIPTION
        "The group of objects that define the alarm thresholds
        on line-level PM counters."

   GROUP  adsl2ChAlarmConfProfileGroup
      DESCRIPTION
        "The group of objects that define the alarm thresholds
        on channel-level PM counters."

   GROUP  adsl2ChConfProfileAtmGroup
      DESCRIPTION
        "The group of configuration objects required when the data
        path is ATM."

   GROUP  adsl2ChConfProfileMinResGroup
      DESCRIPTION
        "The group of configuration objects required for the
        reserved data rate."

   GROUP  adsl2PMLineCurrInitShortGroup
      DESCRIPTION
        "The group of PM counters for the current interval's
        short initializations."

   GROUP  adsl2PMLineInitHist15MinShortGroup
      DESCRIPTION
        "The group of PM counters for the previous 15-minute
        interval's short initializations."

   GROUP  adsl2PMLineInitHist1DayShortGroup



      DESCRIPTION
        "The group of PM counters for the previous 24-hour
        interval's short initializations."

   GROUP  adsl2ScalarSCGroup
      DESCRIPTION
        "The group of objects that report the available memory
        resources for DELT processes."

   GROUP  adsl2ThreshNotificationGroup
      DESCRIPTION
        "The group of threshold crossing notifications."

   GROUP  adsl2StatusChangeNotificationGroup
      DESCRIPTION
        "The group of status change notifications."

      ::= { adsl2Compliances 1 }

   -- units of conformance

   adsl2LineGroup OBJECT-GROUP
      OBJECTS
          {
          adsl2LineCnfgTemplate,
          adsl2LineAlarmCnfgTemplate,
          adsl2LineCmndConfPmsf,
          adsl2LineCmndConfLdsf,
          adsl2LineCmndConfLdsfFailReason,
          adsl2LineCmndAutomodeColdStart,
          adsl2LineStatusAtuTransSys,
          adsl2LineStatusPwrMngState,
          adsl2LineStatusInitResult,
          adsl2LineStatusLastStateDs,
          adsl2LineStatusLastStateUs,
          adsl2LineStatusAtur,
          adsl2LineStatusAtuc,
          adsl2LineStatusLnAttenDs,
          adsl2LineStatusLnAttenUs,
          adsl2LineStatusSigAttenDs,
          adsl2LineStatusSigAttenUs,
          adsl2LineStatusSnrMarginDs,
          adsl2LineStatusSnrMarginUs,
          adsl2LineStatusAttainableRateDs,
          adsl2LineStatusAttainableRateUs,
          adsl2LineStatusActPsdDs,
          adsl2LineStatusActPsdUs,
          adsl2LineStatusActAtpDs,



          adsl2LineStatusActAtpUs
          }
      STATUS     current
      DESCRIPTION
          "The group of configuration, status, and commands objects
          on the line level."
      ::= { adsl2Groups 1 }

   adsl2ChannelStatusGroup OBJECT-GROUP
      OBJECTS
          {
          adsl2ChStatusChannelNum,
          adsl2ChStatusActDataRate,
          adsl2ChStatusPrevDataRate,
          adsl2ChStatusActDelay
          }
      STATUS     current
      DESCRIPTION
          "The group of status objects on the channel level."
      ::= { adsl2Groups 2 }

   adsl2ChannelStatusAtmGroup OBJECT-GROUP
      OBJECTS
          {
          adsl2ChStatusAtmStatus
          }
      STATUS     current
      DESCRIPTION
          "The group of status objects on the data path level
          when it is ATM."
      ::= { adsl2Groups 3 }

   adsl2ChannelStatusPtmGroup OBJECT-GROUP
      OBJECTS
          {
          adsl2ChStatusPtmStatus
          }
      STATUS     current
      DESCRIPTION
          "The group of status objects on the data path level
          when it is PTM."
      ::= { adsl2Groups 4 }

   adsl2SCStatusGroup OBJECT-GROUP
      OBJECTS
          {
          adsl2SCStatusMtime,
          adsl2SCStatusSnr,



          adsl2SCStatusBitsAlloc,
          adsl2SCStatusGainAlloc,
          adsl2SCStatusTssi,
          adsl2SCStatusLinScale,
          adsl2SCStatusLinReal,
          adsl2SCStatusLinImg,
          adsl2SCStatusLogMt,
          adsl2SCStatusLog,
          adsl2SCStatusQlnMt,
          adsl2SCStatusQln,
          adsl2SCStatusLnAtten,
          adsl2SCStatusSigAtten,
          adsl2SCStatusSnrMargin,
          adsl2SCStatusAttainableRate,
          adsl2SCStatusActAtp,
          adsl2SCStatusRowStatus
          }
      STATUS     current
      DESCRIPTION
          "The group of status objects on the sub-carrier level.
          They are updated as a result of a DELT process."
      ::= { adsl2Groups 5 }

   adsl2LineInventoryGroup OBJECT-GROUP
      OBJECTS
          {
          adsl2LInvG994VendorId,
          adsl2LInvSystemVendorId,
          adsl2LInvVersionNumber,
          adsl2LInvSerialNumber,
          adsl2LInvSelfTestResult,
          adsl2LInvTransmissionCapabilities
          }
      STATUS     current
      DESCRIPTION
          "The group of inventory objects per XTU."
      ::= { adsl2Groups 6 }

   adsl2LineConfTemplateGroup OBJECT-GROUP
      OBJECTS
          {
          adsl2LConfTempLineProfile,
          adsl2LConfTempChan1ConfProfile,
          adsl2LConfTempChan1RaRatioDs,
          adsl2LConfTempChan1RaRatioUs,
          adsl2LConfTempChan2ConfProfile,
          adsl2LConfTempChan2RaRatioDs,
          adsl2LConfTempChan2RaRatioUs,



          adsl2LConfTempChan3ConfProfile,
          adsl2LConfTempChan3RaRatioDs,
          adsl2LConfTempChan3RaRatioUs,
          adsl2LConfTempChan4ConfProfile,
          adsl2LConfTempChan4RaRatioDs,
          adsl2LConfTempChan4RaRatioUs,
          adsl2LConfTempRowStatus
          }
      STATUS     current
      DESCRIPTION
          "The group of objects in a line configuration template."
      ::= { adsl2Groups 7 }

   adsl2LineConfProfGroup OBJECT-GROUP
      OBJECTS
          {
          adsl2LConfProfScMaskDs,
          adsl2LConfProfScMaskUs,
          adsl2LConfProfRfiBandsDs,
          adsl2LConfProfRaModeDs,
          adsl2LConfProfRaModeUs,
          adsl2LConfProfTargetSnrmDs,
          adsl2LConfProfTargetSnrmUs,
          adsl2LConfProfMaxSnrmDs,
          adsl2LConfProfMaxSnrmUs,
          adsl2LConfProfMinSnrmDs,
          adsl2LConfProfMinSnrmUs,
          adsl2LConfProfAtuTransSysEna,
          adsl2LConfProfPmMode,
          adsl2LConfProfL0Time,
          adsl2LConfProfL2Time,
          adsl2LConfProfL2Atpr,
          adsl2LConfProfL2Atprt,
          adsl2LConfProfRowStatus
          }
      STATUS     current
      DESCRIPTION
          "The group of objects in a line configuration profile."
      ::= { adsl2Groups 8 }

   adsl2LineConfProfRaGroup OBJECT-GROUP
      OBJECTS
          {
          adsl2LConfProfRaUsNrmDs,
          adsl2LConfProfRaUsNrmUs,
          adsl2LConfProfRaUsTimeDs,
          adsl2LConfProfRaUsTimeUs,
          adsl2LConfProfRaDsNrmsDs,



          adsl2LConfProfRaDsNrmsUs,
          adsl2LConfProfRaDsTimeDs,
          adsl2LConfProfRaDsTimeUs
          }
      STATUS     current
      DESCRIPTION
        "The group of objects required for controlling the rate-
        adaptive behavior of the line."
      ::= { adsl2Groups 9 }

   adsl2LineConfProfMsgMinGroup OBJECT-GROUP
      OBJECTS
          {
          adsl2LConfProfMsgMinUs,
          adsl2LConfProfMsgMinDs
          }
      STATUS     current
      DESCRIPTION
        "The group of objects required for controlling the rate
        reserved for Overhead traffic."
      ::= { adsl2Groups 10 }

   adsl2LineConfProfModeSpecGroup OBJECT-GROUP
      OBJECTS
          {
          adsl2LConfProfMaxNomPsdDs,
          adsl2LConfProfMaxNomPsdUs,
          adsl2LConfProfMaxNomAtpDs,
          adsl2LConfProfMaxNomAtpUs,
          adsl2LConfProfMaxAggRxPwrUs,
          adsl2LConfProfPsdMaskDs,
          adsl2LConfProfPsdMaskUs,
          adsl2LConfProfPsdMaskSelectUs,
          adsl2LConfProfModeSpecRowStatus
          }
      STATUS     current
      DESCRIPTION
          "The group of objects in a line configuration profile
          that have an instance for each operation mode allowed."
      ::= { adsl2Groups 11 }

   adsl2ChConfProfileGroup OBJECT-GROUP
      OBJECTS
          {
          adsl2ChConfProfMinDataRateDs,
          adsl2ChConfProfMinDataRateUs,
          adsl2ChConfProfMaxDataRateDs,
          adsl2ChConfProfMaxDataRateUs,



          adsl2ChConfProfMinDataRateLowPwrDs,
          adsl2ChConfProfMaxDelayDs,
          adsl2ChConfProfMaxDelayUs,
          adsl2ChConfProfMinProtectionDs,
          adsl2ChConfProfMinProtectionUs,
          adsl2ChConfProfMaxBerDs,
          adsl2ChConfProfMaxBerUs,
          adsl2ChConfProfUsDataRateDs,
          adsl2ChConfProfDsDataRateDs,
          adsl2ChConfProfUsDataRateUs,
          adsl2ChConfProfDsDataRateUs,
          adsl2ChConfProfRowStatus
          }
      STATUS     current
      DESCRIPTION
         "The group of objects in a channel configuration profile."
      ::= { adsl2Groups 12 }

   adsl2ChConfProfileAtmGroup OBJECT-GROUP
      OBJECTS
          {
          adsl2ChConfProfImaEnabled,
          adsl2ChStatusAtmStatus
          }
      STATUS     current
      DESCRIPTION
        "The group of configuration objects required when the data
        path is ATM."
      ::= { adsl2Groups 13 }

   adsl2ChConfProfileMinResGroup OBJECT-GROUP
      OBJECTS
          {
          adsl2ChConfProfMinResDataRateDs,
          adsl2ChConfProfMinResDataRateUs
          }
      STATUS     current
      DESCRIPTION
        "The group of configuration objects required for the
        reserved data rate."
      ::= { adsl2Groups 14 }

   adsl2LineAlarmConfTemplateGroup OBJECT-GROUP
      OBJECTS
          {
          adsl2LAlarmConfTempLineProfile,
          adsl2LAlarmConfTempChan1ConfProfile,
          adsl2LAlarmConfTempChan2ConfProfile,



          adsl2LAlarmConfTempChan3ConfProfile,
          adsl2LAlarmConfTempChan4ConfProfile,
          adsl2LAlarmConfTempRowStatus
          }
      STATUS     current
      DESCRIPTION
          "The group of objects in a line alarm
           template."
      ::= { adsl2Groups 15 }

   adsl2LineAlarmConfProfileGroup OBJECT-GROUP
      OBJECTS
          {
          adsl2LineAlarmConfProfileAtucThresh15MinFecs,
          adsl2LineAlarmConfProfileAtucThresh15MinEs,
          adsl2LineAlarmConfProfileAtucThresh15MinSes,
          adsl2LineAlarmConfProfileAtucThresh15MinLoss,
          adsl2LineAlarmConfProfileAtucThresh15MinUas,
          adsl2LineAlarmConfProfileAturThresh15MinFecs,
          adsl2LineAlarmConfProfileAturThresh15MinEs,
          adsl2LineAlarmConfProfileAturThresh15MinSes,
          adsl2LineAlarmConfProfileAturThresh15MinLoss,
          adsl2LineAlarmConfProfileAturThresh15MinUas,
          adsl2LineAlarmConfProfileThresh15MinFailedFullInt,
          adsl2LineAlarmConfProfileThresh15MinFailedShrtInt,
          adsl2LineAlarmConfProfileRowStatus
          }
      STATUS     current
      DESCRIPTION
          "The group of objects in a line alarm profile."
      ::= { adsl2Groups 16 }

   adsl2ChAlarmConfProfileGroup OBJECT-GROUP
      OBJECTS
          {
          adsl2ChAlarmConfProfileAtucThresh15MinCodingViolations,
          adsl2ChAlarmConfProfileAtucThresh15MinCorrected,
          adsl2ChAlarmConfProfileAturThresh15MinCodingViolations,
          adsl2ChAlarmConfProfileAturThresh15MinCorrected,
          adsl2ChAlarmConfProfileRowStatus
          }
      STATUS     current
      DESCRIPTION
          "The group of objects in a channel alarm profile."
      ::= { adsl2Groups 17 }

   adsl2PMLineCurrGroup OBJECT-GROUP
      OBJECTS



          {
          adsl2PMLCurrValidIntervals,
          adsl2PMLCurrInvalidIntervals,
          adsl2PMLCurr15MTimeElapsed,
          adsl2PMLCurr15MFecs,
          adsl2PMLCurr15MEs,
          adsl2PMLCurr15MSes,
          adsl2PMLCurr15MLoss,
          adsl2PMLCurr15MUas,
          adsl2PMLCurr1DayValidIntervals,
          adsl2PMLCurr1DayInvalidIntervals,
          adsl2PMLCurr1DayTimeElapsed,
          adsl2PMLCurr1DayFecs,
          adsl2PMLCurr1DayEs,
          adsl2PMLCurr1DaySes,
          adsl2PMLCurr1DayLoss,
          adsl2PMLCurr1DayUas
          }
      STATUS     current
      DESCRIPTION
        "The group of objects that report the line-level
        counters for current PM intervals."
      ::= { adsl2Groups 18 }

   adsl2PMLineCurrInitGroup OBJECT-GROUP
      OBJECTS
          {
          adsl2PMLCurrInit15MTimeElapsed,
          adsl2PMLCurrInit15MFullInits,
          adsl2PMLCurrInit15MFailedFullInits,
          adsl2PMLCurrInit1DayTimeElapsed,
          adsl2PMLCurrInit1DayFullInits,
          adsl2PMLCurrInit1DayFailedFullInits
          }
      STATUS     current
      DESCRIPTION
        "The group of objects that report the full
        initialization counters for current PM intervals."
      ::= { adsl2Groups 19 }

   adsl2PMLineCurrInitShortGroup OBJECT-GROUP
      OBJECTS
          {
          adsl2PMLCurrInit15MShortInits,
          adsl2PMLCurrInit15MFailedShortInits,
          adsl2PMLCurrInit1DayShortInits,
          adsl2PMLCurrInit1DayFailedShortInits
          }



      STATUS     current
      DESCRIPTION
        "The group of objects that report the short
        initialization counters for current PM intervals."
      ::= { adsl2Groups 20 }

   adsl2PMLineHist15MinGroup OBJECT-GROUP
      OBJECTS
          {
          adsl2PMLHist15MMonitoredTime,
          adsl2PMLHist15MFecs,
          adsl2PMLHist15MEs,
          adsl2PMLHist15MSes,
          adsl2PMLHist15MLoss,
          adsl2PMLHist15MUas,
          adsl2PMLHist15MValidInterval
          }
      STATUS     current
      DESCRIPTION
        "The group of line-level PM counters for the previous
        15-minute interval."
      ::= { adsl2Groups 21 }

   adsl2PMLineHist1DayGroup OBJECT-GROUP
      OBJECTS
          {
          adsl2PMLHist1DMonitoredTime,
          adsl2PMLHist1DFecs,
          adsl2PMLHist1DEs,
          adsl2PMLHist1DSes,
          adsl2PMLHist1DLoss,
          adsl2PMLHist1DUas,
          adsl2PMLHist1DValidInterval
          }
      STATUS     current
      DESCRIPTION
        "The group of line-level PM counters for the previous
        24-hour interval."
      ::= { adsl2Groups 22 }

   adsl2PMLineInitHist15MinGroup OBJECT-GROUP
      OBJECTS
          {
          adsl2PMLHistInit15MMonitoredTime,
          adsl2PMLHistInit15MFullInits,
          adsl2PMLHistInit15MFailedFullInits,
          adsl2PMLHistInit15MValidInterval
          }



      STATUS     current
      DESCRIPTION
        "The group of PM counters for the previous 15-minute
        interval's full initializations."
      ::= { adsl2Groups 23 }

   adsl2PMLineInitHist15MinShortGroup OBJECT-GROUP
      OBJECTS
          {
          adsl2PMLHistInit15MShortInits,
          adsl2PMLHistInit15MFailedShortInits
          }
      STATUS     current
      DESCRIPTION
        "The group of PM counters for the previous 15-minute
        interval's short initializations."
      ::= { adsl2Groups 24 }

   adsl2PMLineInitHist1DayGroup OBJECT-GROUP
      OBJECTS
          {
          adsl2PMLHistinit1DMonitoredTime,
          adsl2PMLHistinit1DFullInits,
          adsl2PMLHistinit1DFailedFullInits,
          adsl2PMLHistinit1DValidInterval
          }
      STATUS     current
      DESCRIPTION
        "The group of PM counters for the previous 24-hour
        interval's full initializations."
      ::= { adsl2Groups 25 }

   adsl2PMLineInitHist1DayShortGroup OBJECT-GROUP
      OBJECTS
          {
          adsl2PMLHistinit1DShortInits,
          adsl2PMLHistinit1DFailedShortInits
          }
      STATUS     current
      DESCRIPTION
        "The group of PM counters for the previous 24-hour
        interval's short initializations."
      ::= { adsl2Groups 26 }

   adsl2PMChCurrGroup OBJECT-GROUP
      OBJECTS
          {
          adsl2PMChCurrValidIntervals,



          adsl2PMChCurrInvalidIntervals,
          adsl2PMChCurr15MTimeElapsed,
          adsl2PMChCurr15MCodingViolations,
          adsl2PMChCurr15MCorrectedBlocks,
          adsl2PMChCurr1DayValidIntervals,
          adsl2PMChCurr1DayInvalidIntervals,
          adsl2PMChCurr1DayTimeElapsed,
          adsl2PMChCurr1DayCodingViolations,
          adsl2PMChCurr1DayCorrectedBlocks
          }
      STATUS     current
      DESCRIPTION
        "The group of objects that report the channel-level
        counters for current PM intervals."
      ::= { adsl2Groups 27 }

   adsl2PMChHist15MinGroup OBJECT-GROUP
      OBJECTS
          {
          adsl2PMChHist15MMonitoredTime,
          adsl2PMChHist15MCodingViolations,
          adsl2PMChHist15MCorrectedBlocks,
          adsl2PMChHist15MValidInterval
          }
      STATUS     current
      DESCRIPTION
        "The group of objects that report the channel-level
        counters for previous 15-minute PM intervals."
      ::= { adsl2Groups 28 }

   adsl2PMChHist1DGroup OBJECT-GROUP
      OBJECTS
          {
          adsl2PMChHist1DMonitoredTime,
          adsl2PMChHist1DCodingViolations,
          adsl2PMChHist1DCorrectedBlocks,
          adsl2PMChHist1DValidInterval
          }
      STATUS     current
      DESCRIPTION
        "The group of objects that report the channel-level
        counters for previous 24-hour PM intervals."
      ::= { adsl2Groups 29 }

   adsl2ScalarSCGroup OBJECT-GROUP
      OBJECTS
          {
          adsl2ScalarSCMaxInterfaces,



          adsl2ScalarSCAvailInterfaces
          }
      STATUS     current
      DESCRIPTION
        "The group of objects that report the available memory
        resources for DELT processes."
      ::= { adsl2Groups 30 }

   adsl2ThreshNotificationGroup NOTIFICATION-GROUP
      NOTIFICATIONS
      {
      adsl2LinePerfFECSThreshAtuc,
      adsl2LinePerfFECSThreshAtur,
      adsl2LinePerfESThreshAtuc,
      adsl2LinePerfESThreshAtur,
      adsl2LinePerfSESThreshAtuc,
      adsl2LinePerfSESThreshAtur,
      adsl2LinePerfLOSSThreshAtuc,
      adsl2LinePerfLOSSThreshAtur,
      adsl2LinePerfUASThreshAtuc,
      adsl2LinePerfUASThreshAtur,
      adsl2LinePerfCodingViolationsThreshAtuc,
      adsl2LinePerfCodingViolationsThreshAtur,
      adsl2LinePerfCorrectedThreshAtuc,
      adsl2LinePerfCorrectedThreshAtur,
      adsl2LinePerfFailedFullInitThresh,
      adsl2LinePerfFailedShortInitThresh
      }
      STATUS      current
      DESCRIPTION
        "This group supports notifications of significant conditions
        associated with ADSL/ADSL2/ADSL2+ lines."
      ::= { adsl2Groups 31 }

   adsl2StatusChangeNotificationGroup NOTIFICATION-GROUP
      NOTIFICATIONS
      {
      adsl2LineStatusChangeAtuc,
      adsl2LineStatusChangeAtur
      }
      STATUS      current
      DESCRIPTION
        "This group supports notifications of threshold crossing
        associated with ADSL/ADSL2/ADSL2+ lines."
      ::= { adsl2Groups 32 }

END
